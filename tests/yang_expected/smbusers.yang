module smbusers {
  yang-version 1.1;
  namespace "aug:smbusers";
  prefix aug;

  import augeas-extension {
    prefix augex;
  }

  augex:augeas-mod-name "SmbUsers";

  list smbusers {
    key "config-file";
    leaf config-file {
      type string;
    }
    list entry-list {
      key "_id";
      ordered-by user;
      leaf _id {
        type uint64;
        description
          "Implicitly generated list key to maintain the order of the augeas data.";
      }
      container entry {
        augex:data-path "$$";
        presence "Config entry.";
        leaf word {
          mandatory true;
          type string {
            pattern "[A-Za-z0-9_.-]+";
          }
        }
        list username-list {
          key "_id";
          min-elements 1;
          ordered-by user;
          leaf _id {
            type uint64;
            description
              "Implicitly generated list key to maintain the order of the augeas data.";
          }
          leaf username {
            mandatory true;
            type string {
              pattern "[^ \t\n]+";
            }
            augex:data-path "username";
          }
        }
      }
    }
  }
}
