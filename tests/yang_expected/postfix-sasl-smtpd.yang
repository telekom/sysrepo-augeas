module postfix-sasl-smtpd {
  yang-version 1.1;
  namespace "aug:postfix-sasl-smtpd";
  prefix aug;

  import augeas-extension {
    prefix augex;
  }

  augex:augeas-mod-name "Postfix_sasl_smtpd";

  list postfix-sasl-smtpd {
    key "config-file";
    leaf config-file {
      type string;
    }
    list entries {
      key "_id";
      min-elements 1;
      ordered-by user;
      leaf _id {
        type uint64;
        description
          "Implicitly generated list key to maintain the order of the augeas data.";
      }
      choice ch-entries {
        mandatory true;
        leaf pwcheck-method {
          type string {
            pattern "[^ \t\n].*[^ \t\n]|[^ \t\n]";
          }
          augex:data-path "pwcheck_method";
        }
        leaf auxprop-plugin {
          type string {
            pattern "[^ \t\n].*[^ \t\n]|[^ \t\n]";
          }
          augex:data-path "auxprop_plugin";
        }
        leaf saslauthd-path {
          type string {
            pattern "[^ \t\n].*[^ \t\n]|[^ \t\n]";
          }
          augex:data-path "saslauthd_path";
        }
        leaf mech-list {
          type string {
            pattern "[^ \t\n].*[^ \t\n]|[^ \t\n]";
          }
          augex:data-path "mech_list";
        }
        leaf sql-engine {
          type string {
            pattern "[^ \t\n].*[^ \t\n]|[^ \t\n]";
          }
          augex:data-path "sql_engine";
        }
        leaf log-level {
          type string {
            pattern "[^ \t\n].*[^ \t\n]|[^ \t\n]";
          }
          augex:data-path "log_level";
        }
        leaf auto-transition {
          type string {
            pattern "[^ \t\n].*[^ \t\n]|[^ \t\n]";
          }
          augex:data-path "auto_transition";
        }
      }
    }
  }
}
