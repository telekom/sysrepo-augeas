module toml {
  yang-version 1.1;
  namespace "aug:toml";
  prefix aug;

  import augeas-extension {
    prefix augex;
  }

  augex:augeas-mod-name "Toml";

  grouping ch-string {
    choice ch-string {
      mandatory true;
      leaf string {
        type string {
          pattern "([^\\\\\"]|\\\\[\"/bfnrtu\\\\])*";
        }
        augex:data-path "string";
      }
      leaf string-multi {
        type string {
          pattern "([^\\\\\"]|\\\\[\"/bfnrtu\\\\])*";
        }
        augex:data-path "string_multi";
      }
      leaf string-literal {
        type string {
          pattern "([^\\\\']|\\\\['/bfnrtu\\\\])*";
        }
        augex:data-path "string_literal";
      }
      leaf integer {
        type string {
          pattern "((([+-]?[0-9_]+)|(0x[A-Za-z0-9]+))|(0o[0-7]+))|(0b[01]+)";
        }
        augex:data-path "integer";
      }
      leaf float {
        type string {
          pattern "(((((([+-]?)([0-9_]+))((\\.)([0-9_]+)))|((([+-]?)([0-9_]+))(([Ee])(([+-]?)([0-9_]+)))))|(((([+-]?)([0-9_]+))((\\.)([0-9_]+)))(([Ee])(([+-]?)([0-9_]+)))))|(([+-]?)(inf)))|(([+-]?)(nan))";
        }
        augex:data-path "float";
      }
      leaf bool {
        type boolean;
        augex:data-path "bool";
      }
      leaf datetime {
        type string {
          pattern "(([0-9]{4}-[0-9]{2}-[0-9]{2})([T ]))([0-9]{1,2}:[0-9]{2}:[0-9]{2}(\\.[0-9]+)?[A-Z]*)";
        }
        augex:data-path "datetime";
      }
      leaf date {
        type string {
          pattern "[0-9]{4}-[0-9]{2}-[0-9]{2}";
        }
        augex:data-path "date";
      }
      leaf time {
        type string {
          pattern "[0-9]{1,2}:[0-9]{2}:[0-9]{2}(\\.[0-9]+)?[A-Z]*";
        }
        augex:data-path "time";
      }
      container array {
        augex:data-path "array";
        presence "Config entry.";
        list norec {
          key "_id";
          ordered-by user;
          leaf _id {
            type uint64;
            description
              "Implicitly generated list key to maintain the order of the augeas data.";
          }
          choice ch-norec {
            mandatory true;
            leaf string {
              type string {
                pattern "([^\\\\\"]|\\\\[\"/bfnrtu\\\\])*";
              }
              augex:data-path "string";
            }
            leaf string-multi {
              type string {
                pattern "([^\\\\\"]|\\\\[\"/bfnrtu\\\\])*";
              }
              augex:data-path "string_multi";
            }
            leaf string-literal {
              type string {
                pattern "([^\\\\']|\\\\['/bfnrtu\\\\])*";
              }
              augex:data-path "string_literal";
            }
            leaf integer {
              type string {
                pattern "((([+-]?[0-9_]+)|(0x[A-Za-z0-9]+))|(0o[0-7]+))|(0b[01]+)";
              }
              augex:data-path "integer";
            }
            leaf float {
              type string {
                pattern "(((((([+-]?)([0-9_]+))((\\.)([0-9_]+)))|((([+-]?)([0-9_]+))(([Ee])(([+-]?)([0-9_]+)))))|(((([+-]?)([0-9_]+))((\\.)([0-9_]+)))(([Ee])(([+-]?)([0-9_]+)))))|(([+-]?)(inf)))|(([+-]?)(nan))";
              }
              augex:data-path "float";
            }
            leaf bool {
              type boolean;
              augex:data-path "bool";
            }
            leaf datetime {
              type string {
                pattern "(([0-9]{4}-[0-9]{2}-[0-9]{2})([T ]))([0-9]{1,2}:[0-9]{2}:[0-9]{2}(\\.[0-9]+)?[A-Z]*)";
              }
              augex:data-path "datetime";
            }
            leaf date {
              type string {
                pattern "[0-9]{4}-[0-9]{2}-[0-9]{2}";
              }
              augex:data-path "date";
            }
            leaf time {
              type string {
                pattern "[0-9]{1,2}:[0-9]{2}:[0-9]{2}(\\.[0-9]+)?[A-Z]*";
              }
              augex:data-path "time";
            }
          }
        }
      }
    }
  }
  grouping entry-list {
    list entry-list {
      key "_id";
      ordered-by user;
      leaf _id {
        type uint64;
        description
          "Implicitly generated list key to maintain the order of the augeas data.";
      }
      container entry {
        augex:data-path "entry";
        augex:value-yang-path "word";
        presence "Config entry.";
        leaf word {
          mandatory true;
          type string {
            pattern "[A-Za-z0-9_.-]+";
          }
        }
        choice ch-entry {
          mandatory true;
          leaf string {
            type string {
              pattern "([^\\\\\"]|\\\\[\"/bfnrtu\\\\])*";
            }
            augex:data-path "string";
          }
          leaf string-multi {
            type string {
              pattern "([^\\\\\"]|\\\\[\"/bfnrtu\\\\])*";
            }
            augex:data-path "string_multi";
          }
          leaf string-literal {
            type string {
              pattern "([^\\\\']|\\\\['/bfnrtu\\\\])*";
            }
            augex:data-path "string_literal";
          }
          leaf integer {
            type string {
              pattern "((([+-]?[0-9_]+)|(0x[A-Za-z0-9]+))|(0o[0-7]+))|(0b[01]+)";
            }
            augex:data-path "integer";
          }
          leaf float {
            type string {
              pattern "(((((([+-]?)([0-9_]+))((\\.)([0-9_]+)))|((([+-]?)([0-9_]+))(([Ee])(([+-]?)([0-9_]+)))))|(((([+-]?)([0-9_]+))((\\.)([0-9_]+)))(([Ee])(([+-]?)([0-9_]+)))))|(([+-]?)(inf)))|(([+-]?)(nan))";
            }
            augex:data-path "float";
          }
          leaf bool {
            type boolean;
            augex:data-path "bool";
          }
          leaf datetime {
            type string {
              pattern "(([0-9]{4}-[0-9]{2}-[0-9]{2})([T ]))([0-9]{1,2}:[0-9]{2}:[0-9]{2}(\\.[0-9]+)?[A-Z]*)";
            }
            augex:data-path "datetime";
          }
          leaf date {
            type string {
              pattern "[0-9]{4}-[0-9]{2}-[0-9]{2}";
            }
            augex:data-path "date";
          }
          leaf time {
            type string {
              pattern "[0-9]{1,2}:[0-9]{2}:[0-9]{2}(\\.[0-9]+)?[A-Z]*";
            }
            augex:data-path "time";
          }
          container array {
            augex:data-path "array";
            presence "Config entry.";
            list ch-string-list {
              key "_id";
              ordered-by user;
              leaf _id {
                type uint64;
                description
                  "Implicitly generated list key to maintain the order of the augeas data.";
              }
              uses ch-string;
            }
          }
          container inline-table {
            augex:data-path "inline_table";
            presence "Config entry.";
            list entry-list {
              key "_id";
              ordered-by user;
              leaf _id {
                type uint64;
                description
                  "Implicitly generated list key to maintain the order of the augeas data.";
              }
              container entry {
                augex:data-path "entry";
                augex:value-yang-path "word";
                presence "Config entry.";
                leaf word {
                  mandatory true;
                  type string {
                    pattern "[A-Za-z0-9_.-]+";
                  }
                }
                uses ch-string;
              }
            }
          }
        }
      }
    }
  }
  list toml {
    key "config-file";
    leaf config-file {
      type string;
    }
    uses entry-list;
    list table {
      key "_id";
      ordered-by user;
      leaf _id {
        type uint64;
        description
          "Implicitly generated list key to maintain the order of the augeas data.";
      }
      choice ch-table {
        mandatory true;
        container table {
          augex:data-path "table";
          augex:value-yang-path "value";
          presence "Config entry.";
          leaf value {
            mandatory true;
            type string {
              pattern "[^\\]\n.]+(\\.[^\\]\n.]+)*";
            }
          }
          uses entry-list;
        }
        container table2 {
          augex:data-path "@table";
          augex:value-yang-path "value";
          presence "Config entry.";
          leaf value {
            mandatory true;
            type string {
              pattern "[^\\]\n.]+(\\.[^\\]\n.]+)*";
            }
          }
          uses entry-list;
        }
      }
    }
  }
}
