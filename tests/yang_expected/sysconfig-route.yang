module sysconfig-route {
  yang-version 1.1;
  namespace "aug:sysconfig-route";
  prefix aug;

  import augeas-extension {
    prefix augex;
  }
  import ietf-inet-types {
    prefix inet;
    reference
      "RFC 6991: Common YANG Data Types";
  }

  augex:augeas-mod-name "Sysconfig_Route";

  list sysconfig-route {
    key "config-file";
    leaf config-file {
      type string;
    }
    list entry-list {
      key "_id";
      min-elements 1;
      ordered-by user;
      leaf _id {
        type uint64;
        description
          "Implicitly generated list key to maintain the order of the augeas data.";
      }
      container entry {
        augex:data-path "$$";
        augex:value-yang-path "subnet";
        presence "Config entry.";
        leaf router {
          mandatory true;
          type inet:ipv4-address-no-zone;
        }
        leaf subnet {
          mandatory true;
          type string {
            pattern "((((((((25[0-5]?|2[0-4][0-9]|1[0-9]{2}|[1-9]?[0-9])(\\.))(25[0-5]?|2[0-4][0-9]|1[0-9]{2}|[1-9]?[0-9]))(\\.))(25[0-5]?|2[0-4][0-9]|1[0-9]{2}|[1-9]?[0-9]))(\\.))(25[0-5]?|2[0-4][0-9]|1[0-9]{2}|[1-9]?[0-9]))(/))((3[012]|[12][0-9]|[0-9]))";
          }
        }
      }
    }
  }
}
