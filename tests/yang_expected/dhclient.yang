module dhclient {
  yang-version 1.1;
  namespace "aug:dhclient";
  prefix aug;

  import augeas-extension {
    prefix augex;
  }

  augex:augeas-mod-name "Dhclient";

  grouping word {
    container word {
      augex:data-path "$$";
      augex:value-yang-path "sto-to-spc-noeval";
      presence "Config entry.";
      leaf word {
        mandatory true;
        type string {
          pattern "[A-Za-z0-9_.-]+(\\[[0-9]+\\])?";
        }
      }
      choice ch-word {
        mandatory true;
        leaf sto-to-spc-noeval {
          type string {
            pattern "[^=\\\\#,;{}\" \t\n]|[^=\\\\#,;{}\" \t\n][^\\\\#,;{}\" \t\n]*|\"[^\\\\#\"\n]+\"";
          }
        }
        case code {
          leaf code {
            mandatory true;
            type string {
              pattern "[A-Za-z0-9_.-]+(\\[[0-9]+\\])?";
            }
            augex:data-path "code";
          }
          leaf value {
            mandatory true;
            type string {
              pattern "[^ \t\n][^;\n]+[^ \t]|[^ \t;\n]+";
            }
            augex:data-path "value";
          }
        }
        leaf eval {
          type string {
            pattern "[^ \t\n][^;\n]+[^ \t]|[^ \t;\n]+";
          }
          augex:data-path "#eval";
        }
      }
    }
  }
  grouping stmt-array-list {
    list stmt-array-list {
      key "_seq";
      min-elements 1;
      ordered-by user;
      augex:data-path "$$";
      augex:value-yang-path "sto-to-spc";
      leaf _seq {
        type uint64;
        description
          "Key contains some unique value. The order is based on the actual order of list instances.";
      }
      leaf sto-to-spc {
        mandatory true;
        type string {
          pattern "[^\\\\#,;{}\" \t\n]+|\"[^\\\\#\"\n]+\"";
        }
      }
    }
  }
  grouping stmt-block-date {
    leaf weekday {
      mandatory true;
      type string {
        pattern "[0-9][0-9]*";
      }
      augex:data-path "weekday";
    }
    leaf year {
      mandatory true;
      type string {
        pattern "[0-9][0-9]*";
      }
      augex:data-path "year";
    }
    leaf month {
      mandatory true;
      type string {
        pattern "[0-9][0-9]*";
      }
      augex:data-path "month";
    }
    leaf day {
      mandatory true;
      type string {
        pattern "[0-9][0-9]*";
      }
      augex:data-path "day";
    }
    leaf hour {
      mandatory true;
      type string {
        pattern "[0-9][0-9]*";
      }
      augex:data-path "hour";
    }
    leaf minute {
      mandatory true;
      type string {
        pattern "[0-9][0-9]*";
      }
      augex:data-path "minute";
    }
    leaf second {
      mandatory true;
      type string {
        pattern "[0-9][0-9]*";
      }
      augex:data-path "second";
    }
  }
  grouping stmt-block-entry {
    list stmt-block-entry {
      key "_id";
      min-elements 1;
      ordered-by user;
      leaf _id {
        type uint64;
        description
          "Implicitly generated list key to maintain the order of the augeas data.";
      }
      choice ch-stmt-block-entry {
        mandatory true;
        container media {
          augex:data-path "media";
          presence "Config entry.";
          uses stmt-array-list;
        }
        container request {
          augex:data-path "request";
          presence "Config entry.";
          uses stmt-array-list;
        }
        container require {
          augex:data-path "require";
          presence "Config entry.";
          uses stmt-array-list;
        }
        container send {
          augex:data-path "send";
          presence "Config entry.";
          uses word;
        }
        container option {
          augex:data-path "option";
          presence "Config entry.";
          uses word;
        }
        container append {
          augex:data-path "append";
          presence "Config entry.";
          uses word;
        }
        container prepend {
          augex:data-path "prepend";
          presence "Config entry.";
          uses word;
        }
        container default {
          augex:data-path "default";
          presence "Config entry.";
          uses word;
        }
        container supersede {
          augex:data-path "supersede";
          presence "Config entry.";
          uses word;
        }
        leaf interface {
          type string {
            pattern "[^\\\\#,;{}\" \t\n]+|\"[^\\\\#\"\n]+\"";
          }
          augex:data-path "interface";
        }
        leaf script {
          type string {
            pattern "[^\\\\#,;{}\" \t\n]+|\"[^\\\\#\"\n]+\"";
          }
          augex:data-path "script";
        }
        leaf bootp {
          type string {
            pattern "[^\\\\#,;{}\" \t\n]+|\"[^\\\\#\"\n]+\"";
          }
          augex:data-path "bootp";
        }
        leaf fixed-address {
          type string {
            pattern "[^\\\\#,;{}\" \t\n]+|\"[^\\\\#\"\n]+\"";
          }
          augex:data-path "fixed-address";
        }
        leaf filename {
          type string {
            pattern "[^\\\\#,;{}\" \t\n]+|\"[^\\\\#\"\n]+\"";
          }
          augex:data-path "filename";
        }
        leaf server-name {
          type string {
            pattern "[^\\\\#,;{}\" \t\n]+|\"[^\\\\#\"\n]+\"";
          }
          augex:data-path "server-name";
        }
        leaf medium {
          type string {
            pattern "[^\\\\#,;{}\" \t\n]+|\"[^\\\\#\"\n]+\"";
          }
          augex:data-path "medium";
        }
        leaf vendor-option-space {
          type string {
            pattern "[^\\\\#,;{}\" \t\n]+|\"[^\\\\#\"\n]+\"";
          }
          augex:data-path "vendor option space";
        }
        container renew {
          augex:data-path "renew";
          presence "Config entry.";
          uses stmt-block-date;
        }
        container rebind {
          augex:data-path "rebind";
          presence "Config entry.";
          uses stmt-block-date;
        }
        container expire {
          augex:data-path "expire";
          presence "Config entry.";
          uses stmt-block-date;
        }
      }
    }
  }
  list dhclient {
    key "config-file";
    leaf config-file {
      type string;
    }
    list config-entries {
      key "_id";
      ordered-by user;
      leaf _id {
        type uint64;
        description
          "Implicitly generated list key to maintain the order of the augeas data.";
      }
      choice ch-config-entries {
        mandatory true;
        leaf timeout {
          type string {
            pattern "[^\\\\#,;{}\" \t\n]+|\"[^\\\\#\"\n]+\"";
          }
          augex:data-path "timeout";
        }
        leaf retry {
          type string {
            pattern "[^\\\\#,;{}\" \t\n]+|\"[^\\\\#\"\n]+\"";
          }
          augex:data-path "retry";
        }
        leaf select-timeout {
          type string {
            pattern "[^\\\\#,;{}\" \t\n]+|\"[^\\\\#\"\n]+\"";
          }
          augex:data-path "select-timeout";
        }
        leaf reboot {
          type string {
            pattern "[^\\\\#,;{}\" \t\n]+|\"[^\\\\#\"\n]+\"";
          }
          augex:data-path "reboot";
        }
        leaf backoff-cutoff {
          type string {
            pattern "[^\\\\#,;{}\" \t\n]+|\"[^\\\\#\"\n]+\"";
          }
          augex:data-path "backoff-cutoff";
        }
        leaf initial-interval {
          type string {
            pattern "[^\\\\#,;{}\" \t\n]+|\"[^\\\\#\"\n]+\"";
          }
          augex:data-path "initial-interval";
        }
        leaf do-forward-updates {
          type string {
            pattern "[^\\\\#,;{}\" \t\n]+|\"[^\\\\#\"\n]+\"";
          }
          augex:data-path "do-forward-updates";
        }
        leaf reject {
          type string {
            pattern "[^\\\\#,;{}\" \t\n]+|\"[^\\\\#\"\n]+\"";
          }
          augex:data-path "reject";
        }
        container append {
          augex:data-path "append";
          presence "Config entry.";
          uses word;
        }
        container prepend {
          augex:data-path "prepend";
          presence "Config entry.";
          uses word;
        }
        container default {
          augex:data-path "default";
          presence "Config entry.";
          uses word;
        }
        container supersede {
          augex:data-path "supersede";
          presence "Config entry.";
          uses word;
        }
        container media {
          augex:data-path "media";
          presence "Config entry.";
          uses stmt-array-list;
        }
        container request {
          augex:data-path "request";
          presence "Config entry.";
          uses stmt-array-list;
        }
        container require {
          augex:data-path "require";
          presence "Config entry.";
          uses stmt-array-list;
        }
        container send {
          augex:data-path "send";
          presence "Config entry.";
          uses word;
        }
        container option {
          augex:data-path "option";
          presence "Config entry.";
          uses word;
        }
        container interface {
          augex:data-path "interface";
          augex:value-yang-path "sto-to-spc";
          presence "Config entry.";
          leaf sto-to-spc {
            type string {
              pattern "[^\\\\#,;{}\" \t\n]+|\"[^\\\\#\"\n]+\"";
            }
          }
          uses stmt-block-entry;
        }
        container lease {
          augex:data-path "lease";
          augex:value-yang-path "sto-to-spc";
          presence "Config entry.";
          leaf sto-to-spc {
            type string {
              pattern "[^\\\\#,;{}\" \t\n]+|\"[^\\\\#\"\n]+\"";
            }
          }
          uses stmt-block-entry;
        }
        container alias {
          augex:data-path "alias";
          augex:value-yang-path "sto-to-spc";
          presence "Config entry.";
          leaf sto-to-spc {
            type string {
              pattern "[^\\\\#,;{}\" \t\n]+|\"[^\\\\#\"\n]+\"";
            }
          }
          uses stmt-block-entry;
        }
      }
    }
  }
}
