module star {
  yang-version 1.1;
  namespace "aug:star";
  prefix aug;

  import augeas-extension {
    prefix augex;
  }

  augex:augeas-mod-name "Star";

  list star {
    key "config-file";
    leaf config-file {
      type string;
    }
    list config-entries {
      key "_id";
      ordered-by user;
      leaf _id {
        type uint64;
        description
          "Implicitly generated list key to maintain the order of the augeas data.";
      }
      choice ch-config-entries {
        mandatory true;
        leaf star-fifosize {
          type string {
            pattern "[0-9x*.a-z]+";
          }
          augex:data-path "STAR_FIFOSIZE";
        }
        leaf star-fifosize-max {
          type string {
            pattern "[0-9x*.a-z]+";
          }
          augex:data-path "STAR_FIFOSIZE_MAX";
        }
        leaf star-fsync {
          type string {
            pattern "N";
          }
          augex:data-path "STAR_FSYNC";
        }
        leaf star-secure-links {
          type string {
            pattern "N";
          }
          augex:data-path "STAR_SECURE_LINKS";
        }
        container archive {
          augex:data-path "$$";
          presence "Config entry.";
          leaf label {
            mandatory true;
            type string {
              pattern "(archive)([0-7])";
            }
          }
          leaf device {
            mandatory true;
            type string {
              pattern "[^ \t\n]+";
            }
            augex:data-path "device";
          }
          leaf block {
            mandatory true;
            type string {
              pattern "[^ \t\n]+";
            }
            augex:data-path "block";
          }
          leaf size {
            mandatory true;
            type string {
              pattern "[^ \t\n]+";
            }
            augex:data-path "size";
          }
          leaf istape {
            type string {
              pattern "[^ \t\n]+";
            }
            augex:data-path "istape";
          }
        }
      }
    }
  }
}
