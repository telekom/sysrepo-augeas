module memcached {
  yang-version 1.1;
  namespace "aug:memcached";
  prefix aug;

  import augeas-extension {
    prefix augex;
  }

  augex:augeas-mod-name "Memcached";

  list memcached {
    key "config-file";
    leaf config-file {
      type string;
    }
    list config-entries {
      key "_id";
      ordered-by user;
      leaf _id {
        type uint64;
        description
          "Implicitly generated list key to maintain the order of the augeas data.";
      }
      choice ch-config-entries {
        mandatory true;
        container entry {
          augex:data-path "$$";
          augex:value-yang-path "val";
          presence "Config entry.";
          leaf option {
            mandatory true;
            type string {
              pattern "[a-zA-Z]";
            }
          }
          leaf val {
            type string {
              pattern "[^# \n\t]+";
            }
          }
        }
        leaf logfile {
          type string {
            pattern "[^# \n\t]+";
          }
          augex:data-path "logfile";
        }
      }
    }
  }
}
