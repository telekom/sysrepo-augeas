module gtkbookmarks {
  yang-version 1.1;
  namespace "aug:gtkbookmarks";
  prefix aug;

  import augeas-extension {
    prefix augex;
  }

  augex:augeas-mod-name "GtkBookmarks";

  list gtkbookmarks {
    key "config-file";
    leaf config-file {
      type string;
    }
    list entry-list {
      key "_id";
      ordered-by user;
      leaf _id {
        type uint64;
        description
          "Implicitly generated list key to maintain the order of the augeas data.";
      }
      container bookmark {
        augex:data-path "bookmark";
        augex:value-yang-path "no-spaces";
        presence "Config entry.";
        leaf no-spaces {
          mandatory true;
          type string {
            pattern "[^ \t\n]+";
          }
        }
        leaf label {
          type string {
            pattern "[^ \t\n].*[^ \t\n]|[^ \t\n]";
          }
          augex:data-path "label";
        }
      }
    }
  }
}
