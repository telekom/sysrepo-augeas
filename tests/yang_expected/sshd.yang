module sshd {
  yang-version 1.1;
  namespace "aug:sshd";
  prefix aug;

  import augeas-extension {
    prefix augex;
  }

  augex:augeas-mod-name "Sshd";

  grouping gr {
    list config-entries {
      key "_id";
      ordered-by user;
      leaf _id {
        type uint64;
        description
          "Implicitly generated list key to maintain the order of the augeas data.";
      }
      choice ch-config-entries {
        mandatory true;
        container accept-env {
          augex:data-path "$$";
          presence "Config entry.";
          leaf accept-env {
            mandatory true;
            type string {
              pattern "(?i)AcceptEnv";
            }
          }
          list accept-env-list {
            key "_seq";
            ordered-by user;
            augex:data-path "$$";
            augex:value-yang-path "value";
            leaf _seq {
              type uint64;
              description
                "Key contains some unique value. The order is based on the actual order of list instances.";
            }
            leaf value {
              type union {
                type string {
                  pattern "[^\"' \t\n=]+";
                }
                type string {
                  pattern "[^\"'\n]*[ \t]+[^\"'\n]*";
                }
              }
            }
          }
        }
        container allow-groups {
          augex:data-path "$$";
          presence "Config entry.";
          leaf allow-groups {
            mandatory true;
            type string {
              pattern "(?i)AllowGroups";
            }
          }
          list allow-groups-list {
            key "_seq";
            ordered-by user;
            augex:data-path "$$";
            augex:value-yang-path "value";
            leaf _seq {
              type uint64;
              description
                "Key contains some unique value. The order is based on the actual order of list instances.";
            }
            leaf value {
              type union {
                type string {
                  pattern "[^\"' \t\n=]+";
                }
                type string {
                  pattern "[^\"'\n]*[ \t]+[^\"'\n]*";
                }
              }
            }
          }
        }
        container allow-users {
          augex:data-path "$$";
          presence "Config entry.";
          leaf allow-users {
            mandatory true;
            type string {
              pattern "(?i)AllowUsers";
            }
          }
          list allow-users-list {
            key "_seq";
            ordered-by user;
            augex:data-path "$$";
            augex:value-yang-path "value";
            leaf _seq {
              type uint64;
              description
                "Key contains some unique value. The order is based on the actual order of list instances.";
            }
            leaf value {
              type union {
                type string {
                  pattern "[^\"' \t\n=]+";
                }
                type string {
                  pattern "[^\"'\n]*[ \t]+[^\"'\n]*";
                }
              }
            }
          }
        }
        container deny-groups {
          augex:data-path "$$";
          presence "Config entry.";
          leaf deny-groups {
            mandatory true;
            type string {
              pattern "(?i)DenyGroups";
            }
          }
          list deny-groups-list {
            key "_seq";
            ordered-by user;
            augex:data-path "$$";
            augex:value-yang-path "value";
            leaf _seq {
              type uint64;
              description
                "Key contains some unique value. The order is based on the actual order of list instances.";
            }
            leaf value {
              type union {
                type string {
                  pattern "[^\"' \t\n=]+";
                }
                type string {
                  pattern "[^\"'\n]*[ \t]+[^\"'\n]*";
                }
              }
            }
          }
        }
        container subsystem {
          augex:data-path "$$";
          presence "Config entry.";
          leaf subsystem {
            mandatory true;
            type string {
              pattern "(?i)Subsystem";
            }
          }
          container subsystemvalue {
            augex:data-path "$$";
            augex:value-yang-path "value";
            presence "Config entry.";
            leaf label {
              mandatory true;
              type string {
                pattern "[A-Za-z0-9\\\\-]+";
              }
            }
            leaf value {
              mandatory true;
              type string {
                pattern "[^ \t\n=](.*[^ \t\n=])?";
              }
            }
          }
        }
        container deny-users {
          augex:data-path "$$";
          presence "Config entry.";
          leaf deny-users {
            mandatory true;
            type string {
              pattern "(?i)DenyUsers";
            }
          }
          list deny-users-list {
            key "_seq";
            ordered-by user;
            augex:data-path "$$";
            augex:value-yang-path "value";
            leaf _seq {
              type uint64;
              description
                "Key contains some unique value. The order is based on the actual order of list instances.";
            }
            leaf value {
              type union {
                type string {
                  pattern "[^\"' \t\n=]+";
                }
                type string {
                  pattern "[^\"'\n]*[ \t]+[^\"'\n]*";
                }
              }
            }
          }
        }
        container macs {
          augex:data-path "$$";
          presence "Config entry.";
          leaf macs {
            mandatory true;
            type string {
              pattern "(?i)MACs";
            }
          }
          list macs-list {
            key "_seq";
            min-elements 1;
            ordered-by user;
            augex:data-path "$$";
            augex:value-yang-path "value";
            leaf _seq {
              type uint64;
              description
                "Key contains some unique value. The order is based on the actual order of list instances.";
            }
            leaf value {
              mandatory true;
              type string {
                pattern "[^, \t\n=]+";
              }
            }
          }
        }
        container ciphers {
          augex:data-path "$$";
          presence "Config entry.";
          leaf ciphers {
            mandatory true;
            type string {
              pattern "(?i)Ciphers";
            }
          }
          list ciphers-list {
            key "_seq";
            min-elements 1;
            ordered-by user;
            augex:data-path "$$";
            augex:value-yang-path "value";
            leaf _seq {
              type uint64;
              description
                "Key contains some unique value. The order is based on the actual order of list instances.";
            }
            leaf value {
              mandatory true;
              type string {
                pattern "[^, \t\n=]+";
              }
            }
          }
        }
        container kexalgorithms {
          augex:data-path "$$";
          presence "Config entry.";
          leaf kex-algorithms {
            mandatory true;
            type string {
              pattern "(?i)KexAlgorithms";
            }
          }
          list kex-algorithms-list {
            key "_seq";
            min-elements 1;
            ordered-by user;
            augex:data-path "$$";
            augex:value-yang-path "value";
            leaf _seq {
              type uint64;
              description
                "Key contains some unique value. The order is based on the actual order of list instances.";
            }
            leaf value {
              mandatory true;
              type string {
                pattern "[^, \t\n=]+";
              }
            }
          }
        }
        container hostkeyalgorithms {
          augex:data-path "$$";
          presence "Config entry.";
          leaf host-key-algorithms {
            mandatory true;
            type string {
              pattern "(?i)HostKeyAlgorithms";
            }
          }
          list host-key-algorithms-list {
            key "_seq";
            min-elements 1;
            ordered-by user;
            augex:data-path "$$";
            augex:value-yang-path "value";
            leaf _seq {
              type uint64;
              description
                "Key contains some unique value. The order is based on the actual order of list instances.";
            }
            leaf value {
              mandatory true;
              type string {
                pattern "[^, \t\n=]+";
              }
            }
          }
        }
        container gssapikexalgorithms {
          augex:data-path "$$";
          presence "Config entry.";
          leaf gssapikex-algorithms {
            mandatory true;
            type string {
              pattern "(?i)GSSAPIKexAlgorithms";
            }
          }
          list gssapikex-algorithms-list {
            key "_seq";
            min-elements 1;
            ordered-by user;
            augex:data-path "$$";
            augex:value-yang-path "value";
            leaf _seq {
              type uint64;
              description
                "Key contains some unique value. The order is based on the actual order of list instances.";
            }
            leaf value {
              mandatory true;
              type string {
                pattern "[^, \t\n=]+";
              }
            }
          }
        }
        container casignaturealgorithms {
          augex:data-path "$$";
          presence "Config entry.";
          leaf casignature-algorithms {
            mandatory true;
            type string {
              pattern "(?i)CASignatureAlgorithms";
            }
          }
          list casignature-algorithms-list {
            key "_seq";
            min-elements 1;
            ordered-by user;
            augex:data-path "$$";
            augex:value-yang-path "value";
            leaf _seq {
              type uint64;
              description
                "Key contains some unique value. The order is based on the actual order of list instances.";
            }
            leaf value {
              mandatory true;
              type string {
                pattern "[^, \t\n=]+";
              }
            }
          }
        }
        container pubkeyacceptedkeytypes {
          augex:data-path "$$";
          presence "Config entry.";
          leaf pubkey-accepted-key-types {
            mandatory true;
            type string {
              pattern "(?i)PubkeyAcceptedKeyTypes";
            }
          }
          list pubkey-accepted-key-types-list {
            key "_seq";
            min-elements 1;
            ordered-by user;
            augex:data-path "$$";
            augex:value-yang-path "value";
            leaf _seq {
              type uint64;
              description
                "Key contains some unique value. The order is based on the actual order of list instances.";
            }
            leaf value {
              mandatory true;
              type string {
                pattern "[^, \t\n=]+";
              }
            }
          }
        }
        container pubkeyacceptedalgorithms {
          augex:data-path "$$";
          presence "Config entry.";
          leaf pubkey-accepted-algorithms {
            mandatory true;
            type string {
              pattern "(?i)PubkeyAcceptedAlgorithms";
            }
          }
          list pubkey-accepted-algorithms-list {
            key "_seq";
            min-elements 1;
            ordered-by user;
            augex:data-path "$$";
            augex:value-yang-path "value";
            leaf _seq {
              type uint64;
              description
                "Key contains some unique value. The order is based on the actual order of list instances.";
            }
            leaf value {
              mandatory true;
              type string {
                pattern "[^, \t\n=]+";
              }
            }
          }
        }
        container other-entry {
          augex:data-path "$$";
          augex:value-yang-path "value";
          presence "Config entry.";
          leaf key {
            mandatory true;
            type string {
              pattern "[A-Za-z0-9]+";
              pattern "(?i)MACs|Match|AcceptEnv|Subsystem|Ciphers|((GSSAPI|)Kex|HostKey|CASignature|PubkeyAccepted)Algorithms|PubkeyAcceptedKeyTypes|(Allow|Deny)(Groups|Users)" {
                modifier invert-match;
              }
            }
          }
          leaf value {
            mandatory true;
            type string {
              pattern "[^ \t\n=]+([ \t=]+[^ \t\n=]+)*";
            }
          }
        }
      }
    }
  }
  list sshd {
    key "config-file";
    leaf config-file {
      type string;
    }
    uses gr;
    list match-list {
      key "_id";
      ordered-by user;
      leaf _id {
        type uint64;
        description
          "Implicitly generated list key to maintain the order of the augeas data.";
      }
      container match {
        augex:data-path "$$";
        presence "Config entry.";
        leaf match {
          mandatory true;
          type string {
            pattern "(?i)Match";
          }
        }
        container condition {
          augex:data-path "Condition";
          presence "Config entry.";
          list condition-entry-list {
            key "_id";
            min-elements 1;
            ordered-by user;
            leaf _id {
              type uint64;
              description
                "Implicitly generated list key to maintain the order of the augeas data.";
            }
            container condition-entry {
              augex:data-path "$$";
              augex:value-yang-path "value";
              presence "Config entry.";
              leaf label {
                mandatory true;
                type string {
                  pattern "[A-Za-z0-9]+";
                }
              }
              leaf value {
                mandatory true;
                type union {
                  type string {
                    pattern "[^\"' \t\n=]+";
                  }
                  type string {
                    pattern "[^\"'\t\n]* [^\"'\t\n]*";
                  }
                }
              }
            }
          }
        }
        container settings {
          augex:data-path "Settings";
          presence "Config entry.";
          uses gr;
        }
      }
    }
  }
}
