module aptconf {
  yang-version 1.1;
  namespace "aug:aptconf";
  prefix aug;

  import augeas-extension {
    prefix augex;
  }

  augex:augeas-mod-name "AptConf";

  list aptconf {
    key "config-file";
    leaf config-file {
      type string;
    }
    list entry {
      key "_id";
      ordered-by user;
      leaf _id {
        type uint64;
        description
          "Implicitly generated list key to maintain the order of the augeas data.";
      }
      choice ch-entry {
        mandatory true;
        list name-list {
          key "_r-id";
          leaf _r-id {
            type uint64;
            description
              "Implicitly generated list key to maintain the recursive augeas data.";
          }
          container name {
            augex:data-path "$$";
            augex:value-yang-path "value";
            presence "Config entry.";
            leaf name {
              mandatory true;
              type string {
                pattern "[0-9A-Za-z][0-9A-Za-z-]*";
              }
            }
            choice ch-name {
              leaf value {
                type string {
                  pattern "[^\"\n]+";
                }
              }
              list entry-noeol {
                key "_id";
                ordered-by user;
                leaf _id {
                  type uint64;
                  description
                    "Implicitly generated list key to maintain the order of the augeas data.";
                }
                choice ch-entry-noeol {
                  mandatory true;
                  leaf _name-ref {
                    type leafref {
                      path "../../../../name-list/_r-id";
                    }
                    description
                      "Implicitly generated leaf to maintain recursive augeas data.";
                  }
                  leaf elem {
                    type string {
                      pattern "[^\"\n]+";
                    }
                    augex:data-path "@elem";
                  }
                }
              }
            }
          }
        }
        leaf include {
          type string {
            pattern "[^ \t\n]+";
          }
          augex:data-path "#include";
        }
        container clear {
          augex:data-path "#clear";
          presence "Config entry.";
          list name-list {
            key "_id";
            min-elements 1;
            ordered-by user;
            leaf _id {
              type uint64;
              description
                "Implicitly generated list key to maintain the order of the augeas data.";
            }
            leaf name {
              mandatory true;
              type string {
                pattern "[0-9A-Za-z][0-9A-Za-z:-]*";
              }
              augex:data-path "name";
            }
          }
        }
      }
    }
  }
}
