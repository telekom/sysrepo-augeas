module systemd {
  yang-version 1.1;
  namespace "aug:systemd";
  prefix aug;

  import augeas-extension {
    prefix augex;
  }

  augex:augeas-mod-name "Systemd";

  list systemd {
    key "config-file";
    leaf config-file {
      type string;
    }
    list include-list {
      key "_id";
      ordered-by user;
      leaf _id {
        type uint64;
        description
          "Implicitly generated list key to maintain the order of the augeas data.";
      }
      leaf include {
        type string {
          pattern "[^# \t\n]*[^# \t\n\\\\]";
        }
        augex:data-path ".include";
      }
    }
    list record-list {
      key "_id";
      ordered-by user;
      leaf _id {
        type uint64;
        description
          "Implicitly generated list key to maintain the order of the augeas data.";
      }
      container record {
        augex:data-path "$$";
        presence "Config entry.";
        leaf record {
          mandatory true;
          type string {
            pattern "#commen((t[^\\]\n/]|[^\\]\n/t])[^\\]\n/]*|())|#comme([^\\]\n/n][^\\]\n/]*|())|#comm([^\\]\n/e][^\\]\n/]*|())|#com([^\\]\n/m][^\\]\n/]*|())|#co([^\\]\n/m][^\\]\n/]*|())|#c([^\\]\n/o][^\\]\n/]*|())|(#[^\\]\n/c]|[^\\]\n#/][^\\]\n/])[^\\]\n/]*|#|[^\\]\n#/]";
          }
        }
        list config-entries {
          key "_id";
          ordered-by user;
          leaf _id {
            type uint64;
            description
              "Implicitly generated list key to maintain the order of the augeas data.";
          }
          choice ch-config-entries {
            mandatory true;
            container description {
              augex:data-path "Description";
              presence "Config entry.";
              leaf value {
                type string {
                  pattern "([^# \t\n\\\\][^#\n\\\\]*[^# \t\n\\\\]|[^# \t\n\\\\])((([ \t]*\\\\\n[ \t]*)([^# \t\n\\\\][^#\n\\\\]*[^# \t\n\\\\]|[^# \t\n\\\\]))*)";
                }
                augex:data-path "value";
              }
            }
            container entry-multi {
              augex:data-path "$$";
              presence "Config entry.";
              leaf entry-multi-kw {
                mandatory true;
                type string {
                  pattern "Descriptio((n[.0-9A-Z_a-z-]|[.0-9A-Z_a-mo-z-])[.0-9A-Z_a-z-]*|())|Descripti([.0-9A-Z_a-np-z-][.0-9A-Z_a-z-]*|())|Descript([.0-9A-Z_a-hj-z-][.0-9A-Z_a-z-]*|())|Descrip([.0-9A-Z_a-su-z-][.0-9A-Z_a-z-]*|())|Descri([.0-9A-Z_a-oq-z-][.0-9A-Z_a-z-]*|())|Descr([.0-9A-Z_a-hj-z-][.0-9A-Z_a-z-]*|())|Desc([.0-9A-Z_a-qs-z-][.0-9A-Z_a-z-]*|())|Des([.0-9A-Z_abd-z-][.0-9A-Z_a-z-]*|())|De([.0-9A-Z_a-rt-z-][.0-9A-Z_a-z-]*|())|Environmen((t[.0-9A-Z_a-z-]|[.0-9A-Z_a-su-z-])[.0-9A-Z_a-z-]*|())|Environme([.0-9A-Z_a-mo-z-][.0-9A-Z_a-z-]*|())|Environm([.0-9A-Z_a-df-z-][.0-9A-Z_a-z-]*|())|Environ([.0-9A-Z_a-ln-z-][.0-9A-Z_a-z-]*|())|Enviro([.0-9A-Z_a-mo-z-][.0-9A-Z_a-z-]*|())|Envir([.0-9A-Z_a-np-z-][.0-9A-Z_a-z-]*|())|Envi([.0-9A-Z_a-qs-z-][.0-9A-Z_a-z-]*|())|Env([.0-9A-Z_a-hj-z-][.0-9A-Z_a-z-]*|())|ExecP(aths|())|Exec([.0-9_-][.0-9A-Z_a-z-]*|[A-OQ-Za-z]|())|Exe([.0-9A-Z_abd-z-][.0-9A-Z_a-z-]*|())|(Ex[.0-9A-Z_a-df-z-]|En[.0-9A-Z_a-uw-z-]|(E[.0-9A-Z_a-mo-wyz-]|D[.0-9A-Z_a-df-z-]|[A-CF-Za-z][.0-9A-Z_a-z-])[.0-9A-Z_a-z-])[.0-9A-Z_a-z-]*|Ex|En|E[.0-9A-Z_a-mo-wyz-]|D[.0-9A-Z_a-df-z-]|[A-CF-Za-z][.0-9A-Z_a-z-]";
                }
              }
              list entry-value-list {
                key "_id";
                ordered-by user;
                leaf _id {
                  type uint64;
                  description
                    "Implicitly generated list key to maintain the order of the augeas data.";
                }
                leaf value {
                  mandatory true;
                  type string {
                    pattern "[^# \t\n]*[^# \t\n\\\\]";
                  }
                  augex:data-path "value";
                }
              }
            }
            container entry-command {
              augex:data-path "$$";
              presence "Config entry.";
              leaf entry-command-kw {
                mandatory true;
                type string {
                  pattern "ExecPath((s[.0-9A-Z_a-z-]|[.0-9A-Z_a-rt-z-])[.0-9A-Z_a-z-]*|())|ExecPat([.0-9A-Z_a-gi-z-][.0-9A-Z_a-z-]*|())|(ExecPa[.0-9A-Z_a-su-z-]|(ExecP[.0-9A-Z_b-z-]|Exec[A-OQ-Za-z][.0-9A-Z_a-z-])[.0-9A-Z_a-z-])[.0-9A-Z_a-z-]*|ExecPa|ExecP[.0-9A-Z_b-z-]|Exec[A-OQ-Za-z][.0-9A-Z_a-z-]";
                }
              }
              leaf ignoreexit {
                type empty;
                augex:data-path "ignoreexit";
              }
              leaf arg0 {
                type empty;
                augex:data-path "arg0";
              }
              leaf command {
                type string {
                  pattern "[^#@ \t\n\\\\-][^#@ \t\n\\\\-][^# \t\n\\\\]*";
                }
                augex:data-path "command";
              }
              container arguments {
                augex:data-path "arguments";
                presence "Config entry.";
                list args-list {
                  key "_seq";
                  min-elements 1;
                  ordered-by user;
                  augex:data-path "$$";
                  augex:value-yang-path "sto-value";
                  leaf _seq {
                    type uint64;
                    description
                      "Key contains some unique value. The order is based on the actual order of list instances.";
                  }
                  leaf sto-value {
                    mandatory true;
                    type string {
                      pattern "[^# \t\n]*[^# \t\n\\\\]";
                    }
                  }
                }
              }
            }
            container environment {
              augex:data-path "Environment";
              presence "Config entry.";
              list env-key-list {
                key "_id";
                min-elements 1;
                ordered-by user;
                leaf _id {
                  type uint64;
                  description
                    "Implicitly generated list key to maintain the order of the augeas data.";
                }
                container env-key {
                  augex:data-path "$$";
                  augex:value-yang-path "value";
                  presence "Config entry.";
                  leaf env-key {
                    mandatory true;
                    type string {
                      pattern "[A-Za-z0-9_]+(\\[[0-9]+\\])?";
                    }
                  }
                  leaf value {
                    type union {
                      type string {
                        pattern "[^#'\" \t\n]*[^#'\" \t\n\\\\]";
                      }
                      type string {
                        pattern "\"[^#\"\t\n]*\"";
                      }
                      type string {
                        pattern "'[^#'\t\n]*'";
                      }
                      type string {
                        pattern "[^#\"'\n]*[ \t]+[^#\"'\n]*";
                      }
                    }
                  }
                }
              }
            }
            leaf include {
              type string {
                pattern "[^# \t\n]*[^# \t\n\\\\]";
              }
              augex:data-path ".include";
            }
          }
        }
      }
    }
  }
}
