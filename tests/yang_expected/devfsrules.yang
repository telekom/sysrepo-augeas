module devfsrules {
  yang-version 1.1;
  namespace "aug:devfsrules";
  prefix aug;

  import augeas-extension {
    prefix augex;
  }

  augex:augeas-mod-name "DevfsRules";

  list devfsrules {
    key "config-file";
    leaf config-file {
      type string;
    }
    list record-list {
      key "_id";
      ordered-by user;
      leaf _id {
        type uint64;
        description
          "Implicitly generated list key to maintain the order of the augeas data.";
      }
      container record {
        augex:data-path "$$";
        presence "Config entry.";
        leaf word {
          mandatory true;
          type string {
            pattern "[A-Za-z0-9_.-]+";
          }
        }
        leaf id {
          mandatory true;
          type uint64;
          augex:data-path "id";
        }
        list entry-list {
          key "_seq";
          ordered-by user;
          augex:data-path "$$";
          augex:value-yang-path "line";
          leaf _seq {
            type uint64;
            description
              "Key contains some unique value. The order is based on the actual order of list instances.";
          }
          leaf line {
            type string {
              pattern "[^\\]\\[#; \t\n][^#;\n]*[^#; \t\n]";
            }
          }
        }
      }
    }
  }
}
