module termcap {
  yang-version 1.1;
  namespace "aug:termcap";
  prefix aug;

  import augeas-extension {
    prefix augex;
  }

  augex:augeas-mod-name "Termcap";

  list termcap {
    key "config-file";
    leaf config-file {
      type string;
    }
    list record-list {
      key "_id";
      ordered-by user;
      leaf _id {
        type uint64;
        description
          "Implicitly generated list key to maintain the order of the augeas data.";
      }
      container record {
        augex:data-path "record";
        presence "Config entry.";
        list name-list {
          key "_id";
          min-elements 1;
          ordered-by user;
          leaf _id {
            type uint64;
            description
              "Implicitly generated list key to maintain the order of the augeas data.";
          }
          leaf name {
            mandatory true;
            type string {
              pattern "[^#:\\\\\\\\\t\n|][^:\\\\\\\\\t\n|]*";
            }
            augex:data-path "name";
          }
        }
        list capability-list {
          key "_id";
          ordered-by user;
          leaf _id {
            type uint64;
            description
              "Implicitly generated list key to maintain the order of the augeas data.";
          }
          leaf capability {
            mandatory true;
            type string {
              pattern "\\.{0,2}([a-zA-Z0-9]{2}|[@#%&*!][a-zA-Z0-9]|k;)(#?@|#[0-9]+|=([^:\\\\\\\\^]|\\\\[0-7]{3}|\\\\[:bBcCeEfFnNrRstT0\\\\^]|^.)*)?";
            }
            augex:data-path "capability";
          }
        }
      }
    }
  }
}
