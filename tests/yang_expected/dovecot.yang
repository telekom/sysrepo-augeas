module dovecot {
  yang-version 1.1;
  namespace "aug:dovecot";
  prefix aug;

  import augeas-extension {
    prefix augex;
  }

  augex:augeas-mod-name "Dovecot";

  grouping entry {
    container entry {
      augex:data-path "$$";
      augex:value-yang-path "value";
      presence "Config entry.";
      leaf keys {
        mandatory true;
        type string {
          pattern "[A-Za-z0-9_.-]+";
          pattern "include|include_try|dict|userdb|passdb|protocol|service|plugin|namespace|map|fields|unix_listener|fifo_listener|inet_listener" {
            modifier invert-match;
          }
        }
      }
      leaf value {
        type string {
          pattern "([^ \t\n]+)((([ \t]+)([^ \t\n]+))*)";
        }
      }
    }
  }
  list dovecot {
    key "config-file";
    leaf config-file {
      type string;
    }
    list config-entries {
      key "_id";
      ordered-by user;
      leaf _id {
        type uint64;
        description
          "Implicitly generated list key to maintain the order of the augeas data.";
      }
      choice ch-config-entries {
        mandatory true;
        case entry {
          uses entry;
        }
        leaf include {
          type string {
            pattern "[^ \t\n]+";
          }
          augex:data-path "include";
        }
        leaf include-try {
          type string {
            pattern "[^ \t\n]+";
          }
          augex:data-path "include_try";
        }
        list dict-list {
          key "_r-id";
          leaf _r-id {
            type uint64;
            description
              "Implicitly generated list key to maintain the recursive augeas data.";
          }
          choice ch-dict-list {
            mandatory true;
            container dict {
              augex:data-path "dict";
              augex:value-yang-path "value";
              presence "Config entry.";
              leaf value {
                type string {
                  pattern "!?[/A-Za-z0-9_-]+";
                }
              }
              list config-entries {
                key "_id";
                ordered-by user;
                leaf _id {
                  type uint64;
                  description
                    "Implicitly generated list key to maintain the order of the augeas data.";
                }
                choice ch-config-entries {
                  mandatory true;
                  case entry {
                    uses entry;
                  }
                  leaf _dict-ref {
                    type leafref {
                      path "../../../../dict-list/_r-id";
                    }
                    description
                      "Implicitly generated leaf to maintain recursive augeas data.";
                  }
                  container mailbox {
                    augex:data-path "mailbox";
                    augex:value-yang-path "value";
                    presence "Config entry.";
                    leaf value {
                      mandatory true;
                      type union {
                        type string {
                          pattern "[^\" \t\n]+";
                        }
                        type string {
                          pattern "[^\"\n]*[ \t]+[^\"\n]*";
                        }
                      }
                    }
                    list entry-list {
                      key "_id";
                      ordered-by user;
                      leaf _id {
                        type uint64;
                        description
                          "Implicitly generated list key to maintain the order of the augeas data.";
                      }
                      uses entry;
                    }
                  }
                }
              }
            }
            container userdb {
              augex:data-path "userdb";
              augex:value-yang-path "value";
              presence "Config entry.";
              leaf value {
                type string {
                  pattern "!?[/A-Za-z0-9_-]+";
                }
              }
              list config-entries {
                key "_id";
                ordered-by user;
                leaf _id {
                  type uint64;
                  description
                    "Implicitly generated list key to maintain the order of the augeas data.";
                }
                choice ch-config-entries {
                  mandatory true;
                  case entry {
                    uses entry;
                  }
                  leaf _dict-ref {
                    type leafref {
                      path "../../../../dict-list/_r-id";
                    }
                    description
                      "Implicitly generated leaf to maintain recursive augeas data.";
                  }
                  container mailbox {
                    augex:data-path "mailbox";
                    augex:value-yang-path "value";
                    presence "Config entry.";
                    leaf value {
                      mandatory true;
                      type union {
                        type string {
                          pattern "[^\" \t\n]+";
                        }
                        type string {
                          pattern "[^\"\n]*[ \t]+[^\"\n]*";
                        }
                      }
                    }
                    list entry-list {
                      key "_id";
                      ordered-by user;
                      leaf _id {
                        type uint64;
                        description
                          "Implicitly generated list key to maintain the order of the augeas data.";
                      }
                      uses entry;
                    }
                  }
                }
              }
            }
            container passdb {
              augex:data-path "passdb";
              augex:value-yang-path "value";
              presence "Config entry.";
              leaf value {
                type string {
                  pattern "!?[/A-Za-z0-9_-]+";
                }
              }
              list config-entries {
                key "_id";
                ordered-by user;
                leaf _id {
                  type uint64;
                  description
                    "Implicitly generated list key to maintain the order of the augeas data.";
                }
                choice ch-config-entries {
                  mandatory true;
                  case entry {
                    uses entry;
                  }
                  leaf _dict-ref {
                    type leafref {
                      path "../../../../dict-list/_r-id";
                    }
                    description
                      "Implicitly generated leaf to maintain recursive augeas data.";
                  }
                  container mailbox {
                    augex:data-path "mailbox";
                    augex:value-yang-path "value";
                    presence "Config entry.";
                    leaf value {
                      mandatory true;
                      type union {
                        type string {
                          pattern "[^\" \t\n]+";
                        }
                        type string {
                          pattern "[^\"\n]*[ \t]+[^\"\n]*";
                        }
                      }
                    }
                    list entry-list {
                      key "_id";
                      ordered-by user;
                      leaf _id {
                        type uint64;
                        description
                          "Implicitly generated list key to maintain the order of the augeas data.";
                      }
                      uses entry;
                    }
                  }
                }
              }
            }
            container protocol {
              augex:data-path "protocol";
              augex:value-yang-path "value";
              presence "Config entry.";
              leaf value {
                type string {
                  pattern "!?[/A-Za-z0-9_-]+";
                }
              }
              list config-entries {
                key "_id";
                ordered-by user;
                leaf _id {
                  type uint64;
                  description
                    "Implicitly generated list key to maintain the order of the augeas data.";
                }
                choice ch-config-entries {
                  mandatory true;
                  case entry {
                    uses entry;
                  }
                  leaf _dict-ref {
                    type leafref {
                      path "../../../../dict-list/_r-id";
                    }
                    description
                      "Implicitly generated leaf to maintain recursive augeas data.";
                  }
                  container mailbox {
                    augex:data-path "mailbox";
                    augex:value-yang-path "value";
                    presence "Config entry.";
                    leaf value {
                      mandatory true;
                      type union {
                        type string {
                          pattern "[^\" \t\n]+";
                        }
                        type string {
                          pattern "[^\"\n]*[ \t]+[^\"\n]*";
                        }
                      }
                    }
                    list entry-list {
                      key "_id";
                      ordered-by user;
                      leaf _id {
                        type uint64;
                        description
                          "Implicitly generated list key to maintain the order of the augeas data.";
                      }
                      uses entry;
                    }
                  }
                }
              }
            }
            container service {
              augex:data-path "service";
              augex:value-yang-path "value";
              presence "Config entry.";
              leaf value {
                type string {
                  pattern "!?[/A-Za-z0-9_-]+";
                }
              }
              list config-entries {
                key "_id";
                ordered-by user;
                leaf _id {
                  type uint64;
                  description
                    "Implicitly generated list key to maintain the order of the augeas data.";
                }
                choice ch-config-entries {
                  mandatory true;
                  case entry {
                    uses entry;
                  }
                  leaf _dict-ref {
                    type leafref {
                      path "../../../../dict-list/_r-id";
                    }
                    description
                      "Implicitly generated leaf to maintain recursive augeas data.";
                  }
                  container mailbox {
                    augex:data-path "mailbox";
                    augex:value-yang-path "value";
                    presence "Config entry.";
                    leaf value {
                      mandatory true;
                      type union {
                        type string {
                          pattern "[^\" \t\n]+";
                        }
                        type string {
                          pattern "[^\"\n]*[ \t]+[^\"\n]*";
                        }
                      }
                    }
                    list entry-list {
                      key "_id";
                      ordered-by user;
                      leaf _id {
                        type uint64;
                        description
                          "Implicitly generated list key to maintain the order of the augeas data.";
                      }
                      uses entry;
                    }
                  }
                }
              }
            }
            container plugin {
              augex:data-path "plugin";
              augex:value-yang-path "value";
              presence "Config entry.";
              leaf value {
                type string {
                  pattern "!?[/A-Za-z0-9_-]+";
                }
              }
              list config-entries {
                key "_id";
                ordered-by user;
                leaf _id {
                  type uint64;
                  description
                    "Implicitly generated list key to maintain the order of the augeas data.";
                }
                choice ch-config-entries {
                  mandatory true;
                  case entry {
                    uses entry;
                  }
                  leaf _dict-ref {
                    type leafref {
                      path "../../../../dict-list/_r-id";
                    }
                    description
                      "Implicitly generated leaf to maintain recursive augeas data.";
                  }
                  container mailbox {
                    augex:data-path "mailbox";
                    augex:value-yang-path "value";
                    presence "Config entry.";
                    leaf value {
                      mandatory true;
                      type union {
                        type string {
                          pattern "[^\" \t\n]+";
                        }
                        type string {
                          pattern "[^\"\n]*[ \t]+[^\"\n]*";
                        }
                      }
                    }
                    list entry-list {
                      key "_id";
                      ordered-by user;
                      leaf _id {
                        type uint64;
                        description
                          "Implicitly generated list key to maintain the order of the augeas data.";
                      }
                      uses entry;
                    }
                  }
                }
              }
            }
            container namespace {
              augex:data-path "namespace";
              augex:value-yang-path "value";
              presence "Config entry.";
              leaf value {
                type string {
                  pattern "!?[/A-Za-z0-9_-]+";
                }
              }
              list config-entries {
                key "_id";
                ordered-by user;
                leaf _id {
                  type uint64;
                  description
                    "Implicitly generated list key to maintain the order of the augeas data.";
                }
                choice ch-config-entries {
                  mandatory true;
                  case entry {
                    uses entry;
                  }
                  leaf _dict-ref {
                    type leafref {
                      path "../../../../dict-list/_r-id";
                    }
                    description
                      "Implicitly generated leaf to maintain recursive augeas data.";
                  }
                  container mailbox {
                    augex:data-path "mailbox";
                    augex:value-yang-path "value";
                    presence "Config entry.";
                    leaf value {
                      mandatory true;
                      type union {
                        type string {
                          pattern "[^\" \t\n]+";
                        }
                        type string {
                          pattern "[^\"\n]*[ \t]+[^\"\n]*";
                        }
                      }
                    }
                    list entry-list {
                      key "_id";
                      ordered-by user;
                      leaf _id {
                        type uint64;
                        description
                          "Implicitly generated list key to maintain the order of the augeas data.";
                      }
                      uses entry;
                    }
                  }
                }
              }
            }
            container map {
              augex:data-path "map";
              augex:value-yang-path "value";
              presence "Config entry.";
              leaf value {
                type string {
                  pattern "!?[/A-Za-z0-9_-]+";
                }
              }
              list config-entries {
                key "_id";
                ordered-by user;
                leaf _id {
                  type uint64;
                  description
                    "Implicitly generated list key to maintain the order of the augeas data.";
                }
                choice ch-config-entries {
                  mandatory true;
                  case entry {
                    uses entry;
                  }
                  leaf _dict-ref {
                    type leafref {
                      path "../../../../dict-list/_r-id";
                    }
                    description
                      "Implicitly generated leaf to maintain recursive augeas data.";
                  }
                  container mailbox {
                    augex:data-path "mailbox";
                    augex:value-yang-path "value";
                    presence "Config entry.";
                    leaf value {
                      mandatory true;
                      type union {
                        type string {
                          pattern "[^\" \t\n]+";
                        }
                        type string {
                          pattern "[^\"\n]*[ \t]+[^\"\n]*";
                        }
                      }
                    }
                    list entry-list {
                      key "_id";
                      ordered-by user;
                      leaf _id {
                        type uint64;
                        description
                          "Implicitly generated list key to maintain the order of the augeas data.";
                      }
                      uses entry;
                    }
                  }
                }
              }
            }
            container fields {
              augex:data-path "fields";
              augex:value-yang-path "value";
              presence "Config entry.";
              leaf value {
                type string {
                  pattern "!?[/A-Za-z0-9_-]+";
                }
              }
              list config-entries {
                key "_id";
                ordered-by user;
                leaf _id {
                  type uint64;
                  description
                    "Implicitly generated list key to maintain the order of the augeas data.";
                }
                choice ch-config-entries {
                  mandatory true;
                  case entry {
                    uses entry;
                  }
                  leaf _dict-ref {
                    type leafref {
                      path "../../../../dict-list/_r-id";
                    }
                    description
                      "Implicitly generated leaf to maintain recursive augeas data.";
                  }
                  container mailbox {
                    augex:data-path "mailbox";
                    augex:value-yang-path "value";
                    presence "Config entry.";
                    leaf value {
                      mandatory true;
                      type union {
                        type string {
                          pattern "[^\" \t\n]+";
                        }
                        type string {
                          pattern "[^\"\n]*[ \t]+[^\"\n]*";
                        }
                      }
                    }
                    list entry-list {
                      key "_id";
                      ordered-by user;
                      leaf _id {
                        type uint64;
                        description
                          "Implicitly generated list key to maintain the order of the augeas data.";
                      }
                      uses entry;
                    }
                  }
                }
              }
            }
            container unix-listener {
              augex:data-path "unix_listener";
              augex:value-yang-path "value";
              presence "Config entry.";
              leaf value {
                type string {
                  pattern "!?[/A-Za-z0-9_-]+";
                }
              }
              list config-entries {
                key "_id";
                ordered-by user;
                leaf _id {
                  type uint64;
                  description
                    "Implicitly generated list key to maintain the order of the augeas data.";
                }
                choice ch-config-entries {
                  mandatory true;
                  case entry {
                    uses entry;
                  }
                  leaf _dict-ref {
                    type leafref {
                      path "../../../../dict-list/_r-id";
                    }
                    description
                      "Implicitly generated leaf to maintain recursive augeas data.";
                  }
                  container mailbox {
                    augex:data-path "mailbox";
                    augex:value-yang-path "value";
                    presence "Config entry.";
                    leaf value {
                      mandatory true;
                      type union {
                        type string {
                          pattern "[^\" \t\n]+";
                        }
                        type string {
                          pattern "[^\"\n]*[ \t]+[^\"\n]*";
                        }
                      }
                    }
                    list entry-list {
                      key "_id";
                      ordered-by user;
                      leaf _id {
                        type uint64;
                        description
                          "Implicitly generated list key to maintain the order of the augeas data.";
                      }
                      uses entry;
                    }
                  }
                }
              }
            }
            container fifo-listener {
              augex:data-path "fifo_listener";
              augex:value-yang-path "value";
              presence "Config entry.";
              leaf value {
                type string {
                  pattern "!?[/A-Za-z0-9_-]+";
                }
              }
              list config-entries {
                key "_id";
                ordered-by user;
                leaf _id {
                  type uint64;
                  description
                    "Implicitly generated list key to maintain the order of the augeas data.";
                }
                choice ch-config-entries {
                  mandatory true;
                  case entry {
                    uses entry;
                  }
                  leaf _dict-ref {
                    type leafref {
                      path "../../../../dict-list/_r-id";
                    }
                    description
                      "Implicitly generated leaf to maintain recursive augeas data.";
                  }
                  container mailbox {
                    augex:data-path "mailbox";
                    augex:value-yang-path "value";
                    presence "Config entry.";
                    leaf value {
                      mandatory true;
                      type union {
                        type string {
                          pattern "[^\" \t\n]+";
                        }
                        type string {
                          pattern "[^\"\n]*[ \t]+[^\"\n]*";
                        }
                      }
                    }
                    list entry-list {
                      key "_id";
                      ordered-by user;
                      leaf _id {
                        type uint64;
                        description
                          "Implicitly generated list key to maintain the order of the augeas data.";
                      }
                      uses entry;
                    }
                  }
                }
              }
            }
            container inet-listener {
              augex:data-path "inet_listener";
              augex:value-yang-path "value";
              presence "Config entry.";
              leaf value {
                type string {
                  pattern "!?[/A-Za-z0-9_-]+";
                }
              }
              list config-entries {
                key "_id";
                ordered-by user;
                leaf _id {
                  type uint64;
                  description
                    "Implicitly generated list key to maintain the order of the augeas data.";
                }
                choice ch-config-entries {
                  mandatory true;
                  case entry {
                    uses entry;
                  }
                  leaf _dict-ref {
                    type leafref {
                      path "../../../../dict-list/_r-id";
                    }
                    description
                      "Implicitly generated leaf to maintain recursive augeas data.";
                  }
                  container mailbox {
                    augex:data-path "mailbox";
                    augex:value-yang-path "value";
                    presence "Config entry.";
                    leaf value {
                      mandatory true;
                      type union {
                        type string {
                          pattern "[^\" \t\n]+";
                        }
                        type string {
                          pattern "[^\"\n]*[ \t]+[^\"\n]*";
                        }
                      }
                    }
                    list entry-list {
                      key "_id";
                      ordered-by user;
                      leaf _id {
                        type uint64;
                        description
                          "Implicitly generated list key to maintain the order of the augeas data.";
                      }
                      uses entry;
                    }
                  }
                }
              }
            }
          }
        }
      }
    }
  }
}
