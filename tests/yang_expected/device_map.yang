module device_map {
  namespace "aug:device_map";
  prefix aug;

  import augeas-extension {
    prefix augex;
  }

  augex:augeas-mod-name "Device_map";

  list device_map {
    key "config-file";
    leaf config-file {
      type string;
    }
    list map-list {
      key "_id";
      ordered-by user;
      leaf _id {
        type uint64;
        description
          "Implicitly generated list key to maintain the order of the augeas data.";
      }
      container map {
        augex:data-path "$$";
        augex:value-yang-path "fspath";
        presence "Config entry.";
        leaf label {
          mandatory true;
          type string {
            pattern "(((h|f|c)d[0-9]+(,[0-9a-zA-Z]+){0,2})|(0x[0-9a-fA-F]+))|([0-9]+)";
          }
        }
        leaf fspath {
          mandatory true;
          type string {
            pattern "[^ \t\n]+";
          }
        }
      }
    }
  }
}
