module postgresql {
  yang-version 1.1;
  namespace "aug:postgresql";
  prefix aug;

  import augeas-extension {
    prefix augex;
  }

  augex:augeas-mod-name "Postgresql";

  list postgresql {
    key "config-file";
    leaf config-file {
      type string;
    }
    list word-list {
      key "_id";
      ordered-by user;
      leaf _id {
        type uint64;
        description
          "Implicitly generated list key to maintain the order of the augeas data.";
      }
      container word {
        augex:data-path "$$";
        augex:value-yang-path "value";
        presence "Config entry.";
        leaf word {
          mandatory true;
          type string {
            pattern "[A-Za-z0-9_.-]+";
          }
        }
        leaf value {
          mandatory true;
          type union {
            type string {
              pattern "([+-]?[0-9]+([.,][0-9]+)?)(([kMG]?B|[m]?s|min|h|d){0,1})";
            }
            type string {
              pattern "[A-Za-z][A-Za-z0-9_-]*";
            }
            type string {
              pattern "([^#'\n]|\\\\')*";
              pattern "[A-Za-z][A-Za-z0-9_-]*|[+-]?[0-9]+([.,][0-9]+)?([kMG]?B|[m]?s|min|h|d)?" {
                modifier invert-match;
              }
            }
          }
        }
      }
    }
  }
}
