module aptcacherngsecurity {
  yang-version 1.1;
  namespace "aug:aptcacherngsecurity";
  prefix aug;

  import augeas-extension {
    prefix augex;
  }

  augex:augeas-mod-name "AptCacherNGSecurity";

  list aptcacherngsecurity {
    key "config-file";
    leaf config-file {
      type string;
    }
    list record-list {
      key "_id";
      ordered-by user;
      leaf _id {
        type uint64;
        description
          "Implicitly generated list key to maintain the order of the augeas data.";
      }
      container admin-auth {
        augex:data-path "AdminAuth";
        presence "Config entry.";
        container authpair {
          augex:data-path "$$";
          augex:value-yang-path "value";
          presence "Config entry.";
          leaf label {
            mandatory true;
            type string {
              pattern "[^ \t:/]*";
            }
          }
          leaf value {
            mandatory true;
            type string {
              pattern "[^: \t\n]*";
            }
          }
        }
      }
    }
  }
}
