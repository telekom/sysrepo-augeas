module shellvars {
  yang-version 1.1;
  namespace "aug:shellvars";
  prefix aug;

  import augeas-extension {
    prefix augex;
  }

  augex:augeas-mod-name "Shellvars";

  grouping export {
    leaf export {
      type empty;
      augex:data-path "export";
    }
    choice ch-export {
      mandatory true;
      leaf simple-value {
        type union {
          type string {
            length 0;
          }
          type string {
            pattern "((((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))|(\\([ \t]*\\))){0,1}";
          }
        }
      }
      list values-list {
        key "_seq";
        ordered-by user;
        augex:data-path "$$";
        augex:value-yang-path "anyquot";
        leaf _seq {
          type uint64;
          description
            "Key contains some unique value. The order is based on the actual order of list instances.";
        }
        leaf anyquot {
          type string {
            pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
          }
        }
      }
    }
  }
  grouping var-action-list {
    list var-action-list {
      key "_seq";
      min-elements 1;
      ordered-by user;
      augex:data-path "$$";
      augex:value-yang-path "value";
      leaf _seq {
        type uint64;
        description
          "Key contains some unique value. The order is based on the actual order of list instances.";
      }
      leaf value {
        mandatory true;
        type union {
          type string {
            pattern "[-A-Za-z0-9_]+(\\[[0-9A-Za-z_,]+\\])?";
            pattern "unset|export" {
              modifier invert-match;
            }
          }
          type string {
            pattern "$\\{![-A-Za-z0-9_]+(\\[[0-9A-Za-z_,]+\\])?unset|export[\\\\*@]\\}";
          }
        }
      }
    }
  }
  grouping ch-and {
    choice ch-and {
      mandatory true;
      leaf and {
        type string {
          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
        }
        augex:data-path "@and";
      }
      leaf or {
        type string {
          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
        }
        augex:data-path "@or";
      }
    }
  }
  grouping key-list {
    list key-list {
      key "_id";
      ordered-by user;
      leaf _id {
        type uint64;
        description
          "Implicitly generated list key to maintain the order of the augeas data.";
      }
      container key {
        augex:data-path "$$";
        augex:value-yang-path "anyquot";
        presence "Config entry.";
        leaf key {
          mandatory true;
          type string {
            pattern "[-A-Za-z0-9_]+(\\[[0-9A-Za-z_,]+\\])?";
            pattern "unset|export" {
              modifier invert-match;
            }
          }
        }
        leaf anyquot {
          mandatory true;
          type string {
            pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
          }
        }
      }
    }
  }
  grouping type {
    leaf type {
      mandatory true;
      type union {
        type string {
          pattern "\\[";
        }
        type string {
          pattern "\\[\\[";
        }
      }
      augex:data-path "type";
    }
    leaf sto-to-semicol {
      mandatory true;
      type string {
        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
      }
    }
    list ch-and-list {
      key "_id";
      ordered-by user;
      leaf _id {
        type uint64;
        description
          "Implicitly generated list key to maintain the order of the augeas data.";
      }
      uses ch-and;
    }
  }
  list shellvars {
    key "config-file";
    leaf config-file {
      type string;
    }
    list config-entries {
      key "_id";
      ordered-by user;
      leaf _id {
        type uint64;
        description
          "Implicitly generated list key to maintain the order of the augeas data.";
      }
      choice ch-config-entries {
        mandatory true;
        leaf source {
          type string {
            pattern "[^;=# \t\n]+([^;=#\n]*[^;=# \t\n]+)*";
          }
          augex:data-path ".source";
        }
        container key {
          augex:data-path "$$";
          augex:value-yang-path "simple-value";
          presence "Config entry.";
          leaf key {
            mandatory true;
            type string {
              pattern "[-A-Za-z0-9_]+(\\[[0-9A-Za-z_,]+\\])?";
              pattern "unset|export" {
                modifier invert-match;
              }
            }
          }
          uses export;
        }
        container unset {
          augex:data-path "@unset";
          presence "Config entry.";
          uses var-action-list;
        }
        container export {
          augex:data-path "@export";
          presence "Config entry.";
          uses var-action-list;
        }
        container builtin {
          augex:data-path "@builtin";
          augex:value-yang-path "shell-builtin-cmds";
          presence "Config entry.";
          leaf shell-builtin-cmds {
            mandatory true;
            type string {
              pattern "(((ulimit)|(shift))|(exit))|(:)";
            }
          }
          leaf args {
            type string {
              pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
            }
            augex:data-path "args";
          }
        }
        leaf return {
          type union {
            type empty;
            type uint64;
          }
          augex:data-path "@return";
        }
        container condition {
          augex:data-path "@condition";
          augex:value-yang-path "sto-to-semicol";
          presence "Config entry.";
          uses type;
        }
        leaf eval {
          type string {
            pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
          }
          augex:data-path "@eval";
        }
        container alias {
          augex:data-path "@alias";
          augex:value-yang-path "key";
          presence "Config entry.";
          leaf key {
            mandatory true;
            type string {
              pattern "[-A-Za-z0-9_]+(\\[[0-9A-Za-z_,]+\\])?";
              pattern "unset|export" {
                modifier invert-match;
              }
            }
          }
          leaf value {
            mandatory true;
            type string {
              pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
            }
            augex:data-path "value";
          }
        }
        list command-list {
          key "_r-id";
          leaf _r-id {
            type uint64;
            description
              "Implicitly generated list key to maintain the recursive augeas data.";
          }
          container command {
            augex:data-path "@command";
            augex:value-yang-path "value";
            presence "Config entry.";
            uses key-list;
            leaf value {
              mandatory true;
              type string {
                pattern "$?[-A-Za-z0-9_./]+";
                pattern "exit|shift|return|ulimit|unset|export|source|\\.|if|for|select|while|until|then|else|fi|done|case|eval|alias" {
                  modifier invert-match;
                }
              }
            }
            leaf arg {
              type string {
                pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
              }
              augex:data-path "@arg";
            }
            choice ch-command {
              container pipe {
                augex:data-path "@pipe";
                presence "Config entry.";
                list config-entries {
                  key "_id";
                  ordered-by user;
                  leaf _id {
                    type uint64;
                    description
                      "Implicitly generated list key to maintain the order of the augeas data.";
                  }
                  leaf _command-ref {
                    type leafref {
                      path "../../../../../command-list/_r-id";
                    }
                    description
                      "Implicitly generated leaf to maintain recursive augeas data.";
                  }
                }
              }
              container and {
                augex:data-path "@and";
                presence "Config entry.";
                list config-entries {
                  key "_id";
                  ordered-by user;
                  leaf _id {
                    type uint64;
                    description
                      "Implicitly generated list key to maintain the order of the augeas data.";
                  }
                  choice ch-config-entries {
                    mandatory true;
                    leaf source {
                      type string {
                        pattern "[^;=# \t\n]+([^;=#\n]*[^;=# \t\n]+)*";
                      }
                      augex:data-path ".source";
                    }
                    container key {
                      augex:data-path "$$";
                      augex:value-yang-path "simple-value";
                      presence "Config entry.";
                      leaf key {
                        mandatory true;
                        type string {
                          pattern "[-A-Za-z0-9_]+(\\[[0-9A-Za-z_,]+\\])?";
                          pattern "unset|export" {
                            modifier invert-match;
                          }
                        }
                      }
                      uses export;
                    }
                    container unset {
                      augex:data-path "@unset";
                      presence "Config entry.";
                      uses var-action-list;
                    }
                    container export {
                      augex:data-path "@export";
                      presence "Config entry.";
                      uses var-action-list;
                    }
                    container builtin {
                      augex:data-path "@builtin";
                      augex:value-yang-path "shell-builtin-cmds";
                      presence "Config entry.";
                      leaf shell-builtin-cmds {
                        mandatory true;
                        type string {
                          pattern "(((ulimit)|(shift))|(exit))|(:)";
                        }
                      }
                      leaf args {
                        type string {
                          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                        }
                        augex:data-path "args";
                      }
                    }
                    leaf return {
                      type union {
                        type empty;
                        type uint64;
                      }
                      augex:data-path "@return";
                    }
                    container condition {
                      augex:data-path "@condition";
                      augex:value-yang-path "sto-to-semicol";
                      presence "Config entry.";
                      uses type;
                    }
                    leaf eval {
                      type string {
                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                      }
                      augex:data-path "@eval";
                    }
                    container alias {
                      augex:data-path "@alias";
                      augex:value-yang-path "key";
                      presence "Config entry.";
                      leaf key {
                        mandatory true;
                        type string {
                          pattern "[-A-Za-z0-9_]+(\\[[0-9A-Za-z_,]+\\])?";
                          pattern "unset|export" {
                            modifier invert-match;
                          }
                        }
                      }
                      leaf value {
                        mandatory true;
                        type string {
                          pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                        }
                        augex:data-path "value";
                      }
                    }
                    leaf _command-ref {
                      type leafref {
                        path "../../../../../command-list/_r-id";
                      }
                      description
                        "Implicitly generated leaf to maintain recursive augeas data.";
                    }
                  }
                }
              }
              container or {
                augex:data-path "@or";
                presence "Config entry.";
                list config-entries {
                  key "_id";
                  ordered-by user;
                  leaf _id {
                    type uint64;
                    description
                      "Implicitly generated list key to maintain the order of the augeas data.";
                  }
                  choice ch-config-entries {
                    mandatory true;
                    leaf source {
                      type string {
                        pattern "[^;=# \t\n]+([^;=#\n]*[^;=# \t\n]+)*";
                      }
                      augex:data-path ".source";
                    }
                    container key {
                      augex:data-path "$$";
                      augex:value-yang-path "simple-value";
                      presence "Config entry.";
                      leaf key {
                        mandatory true;
                        type string {
                          pattern "[-A-Za-z0-9_]+(\\[[0-9A-Za-z_,]+\\])?";
                          pattern "unset|export" {
                            modifier invert-match;
                          }
                        }
                      }
                      uses export;
                    }
                    container unset {
                      augex:data-path "@unset";
                      presence "Config entry.";
                      uses var-action-list;
                    }
                    container export {
                      augex:data-path "@export";
                      presence "Config entry.";
                      uses var-action-list;
                    }
                    container builtin {
                      augex:data-path "@builtin";
                      augex:value-yang-path "shell-builtin-cmds";
                      presence "Config entry.";
                      leaf shell-builtin-cmds {
                        mandatory true;
                        type string {
                          pattern "(((ulimit)|(shift))|(exit))|(:)";
                        }
                      }
                      leaf args {
                        type string {
                          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                        }
                        augex:data-path "args";
                      }
                    }
                    leaf return {
                      type union {
                        type empty;
                        type uint64;
                      }
                      augex:data-path "@return";
                    }
                    container condition {
                      augex:data-path "@condition";
                      augex:value-yang-path "sto-to-semicol";
                      presence "Config entry.";
                      uses type;
                    }
                    leaf eval {
                      type string {
                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                      }
                      augex:data-path "@eval";
                    }
                    container alias {
                      augex:data-path "@alias";
                      augex:value-yang-path "key";
                      presence "Config entry.";
                      leaf key {
                        mandatory true;
                        type string {
                          pattern "[-A-Za-z0-9_]+(\\[[0-9A-Za-z_,]+\\])?";
                          pattern "unset|export" {
                            modifier invert-match;
                          }
                        }
                      }
                      leaf value {
                        mandatory true;
                        type string {
                          pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                        }
                        augex:data-path "value";
                      }
                    }
                    leaf _command-ref {
                      type leafref {
                        path "../../../../../command-list/_r-id";
                      }
                      description
                        "Implicitly generated leaf to maintain recursive augeas data.";
                    }
                  }
                }
              }
            }
          }
        }
        list if-list {
          key "_r-id";
          leaf _r-id {
            type uint64;
            description
              "Implicitly generated list key to maintain the recursive augeas data.";
          }
          choice ch-if-list {
            mandatory true;
            container if {
              augex:data-path "@if";
              augex:value-yang-path "sto-to-semicol";
              presence "Config entry.";
              leaf sto-to-semicol {
                mandatory true;
                type string {
                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                }
              }
              list ch-and-list {
                key "_id";
                ordered-by user;
                leaf _id {
                  type uint64;
                  description
                    "Implicitly generated list key to maintain the order of the augeas data.";
                }
                uses ch-and;
              }
              list config-entries {
                key "_id";
                ordered-by user;
                leaf _id {
                  type uint64;
                  description
                    "Implicitly generated list key to maintain the order of the augeas data.";
                }
                choice ch-config-entries {
                  mandatory true;
                  leaf source {
                    type string {
                      pattern "[^;=# \t\n]+([^;=#\n]*[^;=# \t\n]+)*";
                    }
                    augex:data-path ".source";
                  }
                  container key {
                    augex:data-path "$$";
                    augex:value-yang-path "simple-value";
                    presence "Config entry.";
                    leaf key {
                      mandatory true;
                      type string {
                        pattern "[-A-Za-z0-9_]+(\\[[0-9A-Za-z_,]+\\])?";
                        pattern "unset|export" {
                          modifier invert-match;
                        }
                      }
                    }
                    uses export;
                  }
                  container unset {
                    augex:data-path "@unset";
                    presence "Config entry.";
                    uses var-action-list;
                  }
                  container export {
                    augex:data-path "@export";
                    presence "Config entry.";
                    uses var-action-list;
                  }
                  container builtin {
                    augex:data-path "@builtin";
                    augex:value-yang-path "shell-builtin-cmds";
                    presence "Config entry.";
                    leaf shell-builtin-cmds {
                      mandatory true;
                      type string {
                        pattern "(((ulimit)|(shift))|(exit))|(:)";
                      }
                    }
                    leaf args {
                      type string {
                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                      }
                      augex:data-path "args";
                    }
                  }
                  leaf return {
                    type union {
                      type empty;
                      type uint64;
                    }
                    augex:data-path "@return";
                  }
                  container condition {
                    augex:data-path "@condition";
                    augex:value-yang-path "sto-to-semicol";
                    presence "Config entry.";
                    uses type;
                  }
                  leaf eval {
                    type string {
                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                    }
                    augex:data-path "@eval";
                  }
                  container alias {
                    augex:data-path "@alias";
                    augex:value-yang-path "key";
                    presence "Config entry.";
                    leaf key {
                      mandatory true;
                      type string {
                        pattern "[-A-Za-z0-9_]+(\\[[0-9A-Za-z_,]+\\])?";
                        pattern "unset|export" {
                          modifier invert-match;
                        }
                      }
                    }
                    leaf value {
                      mandatory true;
                      type string {
                        pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                      }
                      augex:data-path "value";
                    }
                  }
                  list command-list {
                    key "_r-id";
                    leaf _r-id {
                      type uint64;
                      description
                        "Implicitly generated list key to maintain the recursive augeas data.";
                    }
                    container command {
                      augex:data-path "@command";
                      augex:value-yang-path "value";
                      presence "Config entry.";
                      uses key-list;
                      leaf value {
                        mandatory true;
                        type string {
                          pattern "$?[-A-Za-z0-9_./]+";
                          pattern "exit|shift|return|ulimit|unset|export|source|\\.|if|for|select|while|until|then|else|fi|done|case|eval|alias" {
                            modifier invert-match;
                          }
                        }
                      }
                      leaf arg {
                        type string {
                          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                        }
                        augex:data-path "@arg";
                      }
                      choice ch-command {
                        container pipe {
                          augex:data-path "@pipe";
                          presence "Config entry.";
                          list config-entries {
                            key "_id";
                            ordered-by user;
                            leaf _id {
                              type uint64;
                              description
                                "Implicitly generated list key to maintain the order of the augeas data.";
                            }
                            leaf _command-ref {
                              type leafref {
                                path "../../../../../command-list/_r-id";
                              }
                              description
                                "Implicitly generated leaf to maintain recursive augeas data.";
                            }
                          }
                        }
                        container and {
                          augex:data-path "@and";
                          presence "Config entry.";
                          list config-entries {
                            key "_id";
                            ordered-by user;
                            leaf _id {
                              type uint64;
                              description
                                "Implicitly generated list key to maintain the order of the augeas data.";
                            }
                            choice ch-config-entries {
                              mandatory true;
                              leaf source {
                                type string {
                                  pattern "[^;=# \t\n]+([^;=#\n]*[^;=# \t\n]+)*";
                                }
                                augex:data-path ".source";
                              }
                              container key {
                                augex:data-path "$$";
                                augex:value-yang-path "simple-value";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                uses export;
                              }
                              container unset {
                                augex:data-path "@unset";
                                presence "Config entry.";
                                uses var-action-list;
                              }
                              container export {
                                augex:data-path "@export";
                                presence "Config entry.";
                                uses var-action-list;
                              }
                              container builtin {
                                augex:data-path "@builtin";
                                augex:value-yang-path "shell-builtin-cmds";
                                presence "Config entry.";
                                leaf shell-builtin-cmds {
                                  mandatory true;
                                  type string {
                                    pattern "(((ulimit)|(shift))|(exit))|(:)";
                                  }
                                }
                                leaf args {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "args";
                                }
                              }
                              leaf return {
                                type union {
                                  type empty;
                                  type uint64;
                                }
                                augex:data-path "@return";
                              }
                              container condition {
                                augex:data-path "@condition";
                                augex:value-yang-path "sto-to-semicol";
                                presence "Config entry.";
                                uses type;
                              }
                              leaf eval {
                                type string {
                                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                }
                                augex:data-path "@eval";
                              }
                              container alias {
                                augex:data-path "@alias";
                                augex:value-yang-path "key";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                leaf value {
                                  mandatory true;
                                  type string {
                                    pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                  }
                                  augex:data-path "value";
                                }
                              }
                              leaf _command-ref {
                                type leafref {
                                  path "../../../../../command-list/_r-id";
                                }
                                description
                                  "Implicitly generated leaf to maintain recursive augeas data.";
                              }
                            }
                          }
                        }
                        container or {
                          augex:data-path "@or";
                          presence "Config entry.";
                          list config-entries {
                            key "_id";
                            ordered-by user;
                            leaf _id {
                              type uint64;
                              description
                                "Implicitly generated list key to maintain the order of the augeas data.";
                            }
                            choice ch-config-entries {
                              mandatory true;
                              leaf source {
                                type string {
                                  pattern "[^;=# \t\n]+([^;=#\n]*[^;=# \t\n]+)*";
                                }
                                augex:data-path ".source";
                              }
                              container key {
                                augex:data-path "$$";
                                augex:value-yang-path "simple-value";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                uses export;
                              }
                              container unset {
                                augex:data-path "@unset";
                                presence "Config entry.";
                                uses var-action-list;
                              }
                              container export {
                                augex:data-path "@export";
                                presence "Config entry.";
                                uses var-action-list;
                              }
                              container builtin {
                                augex:data-path "@builtin";
                                augex:value-yang-path "shell-builtin-cmds";
                                presence "Config entry.";
                                leaf shell-builtin-cmds {
                                  mandatory true;
                                  type string {
                                    pattern "(((ulimit)|(shift))|(exit))|(:)";
                                  }
                                }
                                leaf args {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "args";
                                }
                              }
                              leaf return {
                                type union {
                                  type empty;
                                  type uint64;
                                }
                                augex:data-path "@return";
                              }
                              container condition {
                                augex:data-path "@condition";
                                augex:value-yang-path "sto-to-semicol";
                                presence "Config entry.";
                                uses type;
                              }
                              leaf eval {
                                type string {
                                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                }
                                augex:data-path "@eval";
                              }
                              container alias {
                                augex:data-path "@alias";
                                augex:value-yang-path "key";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                leaf value {
                                  mandatory true;
                                  type string {
                                    pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                  }
                                  augex:data-path "value";
                                }
                              }
                              leaf _command-ref {
                                type leafref {
                                  path "../../../../../command-list/_r-id";
                                }
                                description
                                  "Implicitly generated leaf to maintain recursive augeas data.";
                              }
                            }
                          }
                        }
                      }
                    }
                  }
                  leaf _if-ref {
                    type leafref {
                      path "../../../../if-list/_r-id";
                    }
                    description
                      "Implicitly generated leaf to maintain recursive augeas data.";
                  }
                }
              }
              list elif-list {
                key "_id";
                ordered-by user;
                leaf _id {
                  type uint64;
                  description
                    "Implicitly generated list key to maintain the order of the augeas data.";
                }
                container elif {
                  augex:data-path "@elif";
                  augex:value-yang-path "sto-to-semicol";
                  presence "Config entry.";
                  leaf sto-to-semicol {
                    mandatory true;
                    type string {
                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                    }
                  }
                  list ch-and-list {
                    key "_id";
                    ordered-by user;
                    leaf _id {
                      type uint64;
                      description
                        "Implicitly generated list key to maintain the order of the augeas data.";
                    }
                    uses ch-and;
                  }
                  list config-entries {
                    key "_id";
                    ordered-by user;
                    leaf _id {
                      type uint64;
                      description
                        "Implicitly generated list key to maintain the order of the augeas data.";
                    }
                    choice ch-config-entries {
                      mandatory true;
                      leaf source {
                        type string {
                          pattern "[^;=# \t\n]+([^;=#\n]*[^;=# \t\n]+)*";
                        }
                        augex:data-path ".source";
                      }
                      container key {
                        augex:data-path "$$";
                        augex:value-yang-path "simple-value";
                        presence "Config entry.";
                        leaf key {
                          mandatory true;
                          type string {
                            pattern "[-A-Za-z0-9_]+(\\[[0-9A-Za-z_,]+\\])?";
                            pattern "unset|export" {
                              modifier invert-match;
                            }
                          }
                        }
                        uses export;
                      }
                      container unset {
                        augex:data-path "@unset";
                        presence "Config entry.";
                        uses var-action-list;
                      }
                      container export {
                        augex:data-path "@export";
                        presence "Config entry.";
                        uses var-action-list;
                      }
                      container builtin {
                        augex:data-path "@builtin";
                        augex:value-yang-path "shell-builtin-cmds";
                        presence "Config entry.";
                        leaf shell-builtin-cmds {
                          mandatory true;
                          type string {
                            pattern "(((ulimit)|(shift))|(exit))|(:)";
                          }
                        }
                        leaf args {
                          type string {
                            pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                          }
                          augex:data-path "args";
                        }
                      }
                      leaf return {
                        type union {
                          type empty;
                          type uint64;
                        }
                        augex:data-path "@return";
                      }
                      container condition {
                        augex:data-path "@condition";
                        augex:value-yang-path "sto-to-semicol";
                        presence "Config entry.";
                        uses type;
                      }
                      leaf eval {
                        type string {
                          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                        }
                        augex:data-path "@eval";
                      }
                      container alias {
                        augex:data-path "@alias";
                        augex:value-yang-path "key";
                        presence "Config entry.";
                        leaf key {
                          mandatory true;
                          type string {
                            pattern "[-A-Za-z0-9_]+(\\[[0-9A-Za-z_,]+\\])?";
                            pattern "unset|export" {
                              modifier invert-match;
                            }
                          }
                        }
                        leaf value {
                          mandatory true;
                          type string {
                            pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                          }
                          augex:data-path "value";
                        }
                      }
                      list command-list {
                        key "_r-id";
                        leaf _r-id {
                          type uint64;
                          description
                            "Implicitly generated list key to maintain the recursive augeas data.";
                        }
                        container command {
                          augex:data-path "@command";
                          augex:value-yang-path "value";
                          presence "Config entry.";
                          uses key-list;
                          leaf value {
                            mandatory true;
                            type string {
                              pattern "$?[-A-Za-z0-9_./]+";
                              pattern "exit|shift|return|ulimit|unset|export|source|\\.|if|for|select|while|until|then|else|fi|done|case|eval|alias" {
                                modifier invert-match;
                              }
                            }
                          }
                          leaf arg {
                            type string {
                              pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                            }
                            augex:data-path "@arg";
                          }
                          choice ch-command {
                            container pipe {
                              augex:data-path "@pipe";
                              presence "Config entry.";
                              list config-entries {
                                key "_id";
                                ordered-by user;
                                leaf _id {
                                  type uint64;
                                  description
                                    "Implicitly generated list key to maintain the order of the augeas data.";
                                }
                                leaf _command-ref {
                                  type leafref {
                                    path "../../../../../command-list/_r-id";
                                  }
                                  description
                                    "Implicitly generated leaf to maintain recursive augeas data.";
                                }
                              }
                            }
                            container and {
                              augex:data-path "@and";
                              presence "Config entry.";
                              list config-entries {
                                key "_id";
                                ordered-by user;
                                leaf _id {
                                  type uint64;
                                  description
                                    "Implicitly generated list key to maintain the order of the augeas data.";
                                }
                                choice ch-config-entries {
                                  mandatory true;
                                  leaf source {
                                    type string {
                                      pattern "[^;=# \t\n]+([^;=#\n]*[^;=# \t\n]+)*";
                                    }
                                    augex:data-path ".source";
                                  }
                                  container key {
                                    augex:data-path "$$";
                                    augex:value-yang-path "simple-value";
                                    presence "Config entry.";
                                    leaf key {
                                      mandatory true;
                                      type string {
                                        pattern "[-A-Za-z0-9_]+(\\[[0-9A-Za-z_,]+\\])?";
                                        pattern "unset|export" {
                                          modifier invert-match;
                                        }
                                      }
                                    }
                                    uses export;
                                  }
                                  container unset {
                                    augex:data-path "@unset";
                                    presence "Config entry.";
                                    uses var-action-list;
                                  }
                                  container export {
                                    augex:data-path "@export";
                                    presence "Config entry.";
                                    uses var-action-list;
                                  }
                                  container builtin {
                                    augex:data-path "@builtin";
                                    augex:value-yang-path "shell-builtin-cmds";
                                    presence "Config entry.";
                                    leaf shell-builtin-cmds {
                                      mandatory true;
                                      type string {
                                        pattern "(((ulimit)|(shift))|(exit))|(:)";
                                      }
                                    }
                                    leaf args {
                                      type string {
                                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                      }
                                      augex:data-path "args";
                                    }
                                  }
                                  leaf return {
                                    type union {
                                      type empty;
                                      type uint64;
                                    }
                                    augex:data-path "@return";
                                  }
                                  container condition {
                                    augex:data-path "@condition";
                                    augex:value-yang-path "sto-to-semicol";
                                    presence "Config entry.";
                                    uses type;
                                  }
                                  leaf eval {
                                    type string {
                                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                    }
                                    augex:data-path "@eval";
                                  }
                                  container alias {
                                    augex:data-path "@alias";
                                    augex:value-yang-path "key";
                                    presence "Config entry.";
                                    leaf key {
                                      mandatory true;
                                      type string {
                                        pattern "[-A-Za-z0-9_]+(\\[[0-9A-Za-z_,]+\\])?";
                                        pattern "unset|export" {
                                          modifier invert-match;
                                        }
                                      }
                                    }
                                    leaf value {
                                      mandatory true;
                                      type string {
                                        pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                      }
                                      augex:data-path "value";
                                    }
                                  }
                                  leaf _command-ref {
                                    type leafref {
                                      path "../../../../../command-list/_r-id";
                                    }
                                    description
                                      "Implicitly generated leaf to maintain recursive augeas data.";
                                  }
                                }
                              }
                            }
                            container or {
                              augex:data-path "@or";
                              presence "Config entry.";
                              list config-entries {
                                key "_id";
                                ordered-by user;
                                leaf _id {
                                  type uint64;
                                  description
                                    "Implicitly generated list key to maintain the order of the augeas data.";
                                }
                                choice ch-config-entries {
                                  mandatory true;
                                  leaf source {
                                    type string {
                                      pattern "[^;=# \t\n]+([^;=#\n]*[^;=# \t\n]+)*";
                                    }
                                    augex:data-path ".source";
                                  }
                                  container key {
                                    augex:data-path "$$";
                                    augex:value-yang-path "simple-value";
                                    presence "Config entry.";
                                    leaf key {
                                      mandatory true;
                                      type string {
                                        pattern "[-A-Za-z0-9_]+(\\[[0-9A-Za-z_,]+\\])?";
                                        pattern "unset|export" {
                                          modifier invert-match;
                                        }
                                      }
                                    }
                                    uses export;
                                  }
                                  container unset {
                                    augex:data-path "@unset";
                                    presence "Config entry.";
                                    uses var-action-list;
                                  }
                                  container export {
                                    augex:data-path "@export";
                                    presence "Config entry.";
                                    uses var-action-list;
                                  }
                                  container builtin {
                                    augex:data-path "@builtin";
                                    augex:value-yang-path "shell-builtin-cmds";
                                    presence "Config entry.";
                                    leaf shell-builtin-cmds {
                                      mandatory true;
                                      type string {
                                        pattern "(((ulimit)|(shift))|(exit))|(:)";
                                      }
                                    }
                                    leaf args {
                                      type string {
                                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                      }
                                      augex:data-path "args";
                                    }
                                  }
                                  leaf return {
                                    type union {
                                      type empty;
                                      type uint64;
                                    }
                                    augex:data-path "@return";
                                  }
                                  container condition {
                                    augex:data-path "@condition";
                                    augex:value-yang-path "sto-to-semicol";
                                    presence "Config entry.";
                                    uses type;
                                  }
                                  leaf eval {
                                    type string {
                                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                    }
                                    augex:data-path "@eval";
                                  }
                                  container alias {
                                    augex:data-path "@alias";
                                    augex:value-yang-path "key";
                                    presence "Config entry.";
                                    leaf key {
                                      mandatory true;
                                      type string {
                                        pattern "[-A-Za-z0-9_]+(\\[[0-9A-Za-z_,]+\\])?";
                                        pattern "unset|export" {
                                          modifier invert-match;
                                        }
                                      }
                                    }
                                    leaf value {
                                      mandatory true;
                                      type string {
                                        pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                      }
                                      augex:data-path "value";
                                    }
                                  }
                                  leaf _command-ref {
                                    type leafref {
                                      path "../../../../../command-list/_r-id";
                                    }
                                    description
                                      "Implicitly generated leaf to maintain recursive augeas data.";
                                  }
                                }
                              }
                            }
                          }
                        }
                      }
                      leaf _if-ref {
                        type leafref {
                          path "../../../../../../if-list/_r-id";
                        }
                        description
                          "Implicitly generated leaf to maintain recursive augeas data.";
                      }
                    }
                  }
                }
              }
              container else {
                augex:data-path "@else";
                presence "Config entry.";
                list config-entries {
                  key "_id";
                  ordered-by user;
                  leaf _id {
                    type uint64;
                    description
                      "Implicitly generated list key to maintain the order of the augeas data.";
                  }
                  choice ch-config-entries {
                    mandatory true;
                    leaf source {
                      type string {
                        pattern "[^;=# \t\n]+([^;=#\n]*[^;=# \t\n]+)*";
                      }
                      augex:data-path ".source";
                    }
                    container key {
                      augex:data-path "$$";
                      augex:value-yang-path "simple-value";
                      presence "Config entry.";
                      leaf key {
                        mandatory true;
                        type string {
                          pattern "[-A-Za-z0-9_]+(\\[[0-9A-Za-z_,]+\\])?";
                          pattern "unset|export" {
                            modifier invert-match;
                          }
                        }
                      }
                      uses export;
                    }
                    container unset {
                      augex:data-path "@unset";
                      presence "Config entry.";
                      uses var-action-list;
                    }
                    container export {
                      augex:data-path "@export";
                      presence "Config entry.";
                      uses var-action-list;
                    }
                    container builtin {
                      augex:data-path "@builtin";
                      augex:value-yang-path "shell-builtin-cmds";
                      presence "Config entry.";
                      leaf shell-builtin-cmds {
                        mandatory true;
                        type string {
                          pattern "(((ulimit)|(shift))|(exit))|(:)";
                        }
                      }
                      leaf args {
                        type string {
                          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                        }
                        augex:data-path "args";
                      }
                    }
                    leaf return {
                      type union {
                        type empty;
                        type uint64;
                      }
                      augex:data-path "@return";
                    }
                    container condition {
                      augex:data-path "@condition";
                      augex:value-yang-path "sto-to-semicol";
                      presence "Config entry.";
                      uses type;
                    }
                    leaf eval {
                      type string {
                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                      }
                      augex:data-path "@eval";
                    }
                    container alias {
                      augex:data-path "@alias";
                      augex:value-yang-path "key";
                      presence "Config entry.";
                      leaf key {
                        mandatory true;
                        type string {
                          pattern "[-A-Za-z0-9_]+(\\[[0-9A-Za-z_,]+\\])?";
                          pattern "unset|export" {
                            modifier invert-match;
                          }
                        }
                      }
                      leaf value {
                        mandatory true;
                        type string {
                          pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                        }
                        augex:data-path "value";
                      }
                    }
                    list command-list {
                      key "_r-id";
                      leaf _r-id {
                        type uint64;
                        description
                          "Implicitly generated list key to maintain the recursive augeas data.";
                      }
                      container command {
                        augex:data-path "@command";
                        augex:value-yang-path "value";
                        presence "Config entry.";
                        uses key-list;
                        leaf value {
                          mandatory true;
                          type string {
                            pattern "$?[-A-Za-z0-9_./]+";
                            pattern "exit|shift|return|ulimit|unset|export|source|\\.|if|for|select|while|until|then|else|fi|done|case|eval|alias" {
                              modifier invert-match;
                            }
                          }
                        }
                        leaf arg {
                          type string {
                            pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                          }
                          augex:data-path "@arg";
                        }
                        choice ch-command {
                          container pipe {
                            augex:data-path "@pipe";
                            presence "Config entry.";
                            list config-entries {
                              key "_id";
                              ordered-by user;
                              leaf _id {
                                type uint64;
                                description
                                  "Implicitly generated list key to maintain the order of the augeas data.";
                              }
                              leaf _command-ref {
                                type leafref {
                                  path "../../../../../command-list/_r-id";
                                }
                                description
                                  "Implicitly generated leaf to maintain recursive augeas data.";
                              }
                            }
                          }
                          container and {
                            augex:data-path "@and";
                            presence "Config entry.";
                            list config-entries {
                              key "_id";
                              ordered-by user;
                              leaf _id {
                                type uint64;
                                description
                                  "Implicitly generated list key to maintain the order of the augeas data.";
                              }
                              choice ch-config-entries {
                                mandatory true;
                                leaf source {
                                  type string {
                                    pattern "[^;=# \t\n]+([^;=#\n]*[^;=# \t\n]+)*";
                                  }
                                  augex:data-path ".source";
                                }
                                container key {
                                  augex:data-path "$$";
                                  augex:value-yang-path "simple-value";
                                  presence "Config entry.";
                                  leaf key {
                                    mandatory true;
                                    type string {
                                      pattern "[-A-Za-z0-9_]+(\\[[0-9A-Za-z_,]+\\])?";
                                      pattern "unset|export" {
                                        modifier invert-match;
                                      }
                                    }
                                  }
                                  uses export;
                                }
                                container unset {
                                  augex:data-path "@unset";
                                  presence "Config entry.";
                                  uses var-action-list;
                                }
                                container export {
                                  augex:data-path "@export";
                                  presence "Config entry.";
                                  uses var-action-list;
                                }
                                container builtin {
                                  augex:data-path "@builtin";
                                  augex:value-yang-path "shell-builtin-cmds";
                                  presence "Config entry.";
                                  leaf shell-builtin-cmds {
                                    mandatory true;
                                    type string {
                                      pattern "(((ulimit)|(shift))|(exit))|(:)";
                                    }
                                  }
                                  leaf args {
                                    type string {
                                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                    }
                                    augex:data-path "args";
                                  }
                                }
                                leaf return {
                                  type union {
                                    type empty;
                                    type uint64;
                                  }
                                  augex:data-path "@return";
                                }
                                container condition {
                                  augex:data-path "@condition";
                                  augex:value-yang-path "sto-to-semicol";
                                  presence "Config entry.";
                                  uses type;
                                }
                                leaf eval {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "@eval";
                                }
                                container alias {
                                  augex:data-path "@alias";
                                  augex:value-yang-path "key";
                                  presence "Config entry.";
                                  leaf key {
                                    mandatory true;
                                    type string {
                                      pattern "[-A-Za-z0-9_]+(\\[[0-9A-Za-z_,]+\\])?";
                                      pattern "unset|export" {
                                        modifier invert-match;
                                      }
                                    }
                                  }
                                  leaf value {
                                    mandatory true;
                                    type string {
                                      pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                    }
                                    augex:data-path "value";
                                  }
                                }
                                leaf _command-ref {
                                  type leafref {
                                    path "../../../../../command-list/_r-id";
                                  }
                                  description
                                    "Implicitly generated leaf to maintain recursive augeas data.";
                                }
                              }
                            }
                          }
                          container or {
                            augex:data-path "@or";
                            presence "Config entry.";
                            list config-entries {
                              key "_id";
                              ordered-by user;
                              leaf _id {
                                type uint64;
                                description
                                  "Implicitly generated list key to maintain the order of the augeas data.";
                              }
                              choice ch-config-entries {
                                mandatory true;
                                leaf source {
                                  type string {
                                    pattern "[^;=# \t\n]+([^;=#\n]*[^;=# \t\n]+)*";
                                  }
                                  augex:data-path ".source";
                                }
                                container key {
                                  augex:data-path "$$";
                                  augex:value-yang-path "simple-value";
                                  presence "Config entry.";
                                  leaf key {
                                    mandatory true;
                                    type string {
                                      pattern "[-A-Za-z0-9_]+(\\[[0-9A-Za-z_,]+\\])?";
                                      pattern "unset|export" {
                                        modifier invert-match;
                                      }
                                    }
                                  }
                                  uses export;
                                }
                                container unset {
                                  augex:data-path "@unset";
                                  presence "Config entry.";
                                  uses var-action-list;
                                }
                                container export {
                                  augex:data-path "@export";
                                  presence "Config entry.";
                                  uses var-action-list;
                                }
                                container builtin {
                                  augex:data-path "@builtin";
                                  augex:value-yang-path "shell-builtin-cmds";
                                  presence "Config entry.";
                                  leaf shell-builtin-cmds {
                                    mandatory true;
                                    type string {
                                      pattern "(((ulimit)|(shift))|(exit))|(:)";
                                    }
                                  }
                                  leaf args {
                                    type string {
                                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                    }
                                    augex:data-path "args";
                                  }
                                }
                                leaf return {
                                  type union {
                                    type empty;
                                    type uint64;
                                  }
                                  augex:data-path "@return";
                                }
                                container condition {
                                  augex:data-path "@condition";
                                  augex:value-yang-path "sto-to-semicol";
                                  presence "Config entry.";
                                  uses type;
                                }
                                leaf eval {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "@eval";
                                }
                                container alias {
                                  augex:data-path "@alias";
                                  augex:value-yang-path "key";
                                  presence "Config entry.";
                                  leaf key {
                                    mandatory true;
                                    type string {
                                      pattern "[-A-Za-z0-9_]+(\\[[0-9A-Za-z_,]+\\])?";
                                      pattern "unset|export" {
                                        modifier invert-match;
                                      }
                                    }
                                  }
                                  leaf value {
                                    mandatory true;
                                    type string {
                                      pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                    }
                                    augex:data-path "value";
                                  }
                                }
                                leaf _command-ref {
                                  type leafref {
                                    path "../../../../../command-list/_r-id";
                                  }
                                  description
                                    "Implicitly generated leaf to maintain recursive augeas data.";
                                }
                              }
                            }
                          }
                        }
                      }
                    }
                    leaf _if-ref {
                      type leafref {
                        path "../../../../../if-list/_r-id";
                      }
                      description
                        "Implicitly generated leaf to maintain recursive augeas data.";
                    }
                  }
                }
              }
            }
            container for {
              augex:data-path "@for";
              augex:value-yang-path "sto-to-semicol";
              presence "Config entry.";
              leaf sto-to-semicol {
                mandatory true;
                type string {
                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                }
              }
              list ch-and-list {
                key "_id";
                ordered-by user;
                leaf _id {
                  type uint64;
                  description
                    "Implicitly generated list key to maintain the order of the augeas data.";
                }
                uses ch-and;
              }
              list config-entries {
                key "_id";
                ordered-by user;
                leaf _id {
                  type uint64;
                  description
                    "Implicitly generated list key to maintain the order of the augeas data.";
                }
                choice ch-config-entries {
                  mandatory true;
                  leaf source {
                    type string {
                      pattern "[^;=# \t\n]+([^;=#\n]*[^;=# \t\n]+)*";
                    }
                    augex:data-path ".source";
                  }
                  container key {
                    augex:data-path "$$";
                    augex:value-yang-path "simple-value";
                    presence "Config entry.";
                    leaf key {
                      mandatory true;
                      type string {
                        pattern "[-A-Za-z0-9_]+(\\[[0-9A-Za-z_,]+\\])?";
                        pattern "unset|export" {
                          modifier invert-match;
                        }
                      }
                    }
                    uses export;
                  }
                  container unset {
                    augex:data-path "@unset";
                    presence "Config entry.";
                    uses var-action-list;
                  }
                  container export {
                    augex:data-path "@export";
                    presence "Config entry.";
                    uses var-action-list;
                  }
                  container builtin {
                    augex:data-path "@builtin";
                    augex:value-yang-path "shell-builtin-cmds";
                    presence "Config entry.";
                    leaf shell-builtin-cmds {
                      mandatory true;
                      type string {
                        pattern "(((ulimit)|(shift))|(exit))|(:)";
                      }
                    }
                    leaf args {
                      type string {
                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                      }
                      augex:data-path "args";
                    }
                  }
                  leaf return {
                    type union {
                      type empty;
                      type uint64;
                    }
                    augex:data-path "@return";
                  }
                  container condition {
                    augex:data-path "@condition";
                    augex:value-yang-path "sto-to-semicol";
                    presence "Config entry.";
                    uses type;
                  }
                  leaf eval {
                    type string {
                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                    }
                    augex:data-path "@eval";
                  }
                  container alias {
                    augex:data-path "@alias";
                    augex:value-yang-path "key";
                    presence "Config entry.";
                    leaf key {
                      mandatory true;
                      type string {
                        pattern "[-A-Za-z0-9_]+(\\[[0-9A-Za-z_,]+\\])?";
                        pattern "unset|export" {
                          modifier invert-match;
                        }
                      }
                    }
                    leaf value {
                      mandatory true;
                      type string {
                        pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                      }
                      augex:data-path "value";
                    }
                  }
                  list command-list {
                    key "_r-id";
                    leaf _r-id {
                      type uint64;
                      description
                        "Implicitly generated list key to maintain the recursive augeas data.";
                    }
                    container command {
                      augex:data-path "@command";
                      augex:value-yang-path "value";
                      presence "Config entry.";
                      uses key-list;
                      leaf value {
                        mandatory true;
                        type string {
                          pattern "$?[-A-Za-z0-9_./]+";
                          pattern "exit|shift|return|ulimit|unset|export|source|\\.|if|for|select|while|until|then|else|fi|done|case|eval|alias" {
                            modifier invert-match;
                          }
                        }
                      }
                      leaf arg {
                        type string {
                          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                        }
                        augex:data-path "@arg";
                      }
                      choice ch-command {
                        container pipe {
                          augex:data-path "@pipe";
                          presence "Config entry.";
                          list config-entries {
                            key "_id";
                            ordered-by user;
                            leaf _id {
                              type uint64;
                              description
                                "Implicitly generated list key to maintain the order of the augeas data.";
                            }
                            leaf _command-ref {
                              type leafref {
                                path "../../../../../command-list/_r-id";
                              }
                              description
                                "Implicitly generated leaf to maintain recursive augeas data.";
                            }
                          }
                        }
                        container and {
                          augex:data-path "@and";
                          presence "Config entry.";
                          list config-entries {
                            key "_id";
                            ordered-by user;
                            leaf _id {
                              type uint64;
                              description
                                "Implicitly generated list key to maintain the order of the augeas data.";
                            }
                            choice ch-config-entries {
                              mandatory true;
                              leaf source {
                                type string {
                                  pattern "[^;=# \t\n]+([^;=#\n]*[^;=# \t\n]+)*";
                                }
                                augex:data-path ".source";
                              }
                              container key {
                                augex:data-path "$$";
                                augex:value-yang-path "simple-value";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                uses export;
                              }
                              container unset {
                                augex:data-path "@unset";
                                presence "Config entry.";
                                uses var-action-list;
                              }
                              container export {
                                augex:data-path "@export";
                                presence "Config entry.";
                                uses var-action-list;
                              }
                              container builtin {
                                augex:data-path "@builtin";
                                augex:value-yang-path "shell-builtin-cmds";
                                presence "Config entry.";
                                leaf shell-builtin-cmds {
                                  mandatory true;
                                  type string {
                                    pattern "(((ulimit)|(shift))|(exit))|(:)";
                                  }
                                }
                                leaf args {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "args";
                                }
                              }
                              leaf return {
                                type union {
                                  type empty;
                                  type uint64;
                                }
                                augex:data-path "@return";
                              }
                              container condition {
                                augex:data-path "@condition";
                                augex:value-yang-path "sto-to-semicol";
                                presence "Config entry.";
                                uses type;
                              }
                              leaf eval {
                                type string {
                                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                }
                                augex:data-path "@eval";
                              }
                              container alias {
                                augex:data-path "@alias";
                                augex:value-yang-path "key";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                leaf value {
                                  mandatory true;
                                  type string {
                                    pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                  }
                                  augex:data-path "value";
                                }
                              }
                              leaf _command-ref {
                                type leafref {
                                  path "../../../../../command-list/_r-id";
                                }
                                description
                                  "Implicitly generated leaf to maintain recursive augeas data.";
                              }
                            }
                          }
                        }
                        container or {
                          augex:data-path "@or";
                          presence "Config entry.";
                          list config-entries {
                            key "_id";
                            ordered-by user;
                            leaf _id {
                              type uint64;
                              description
                                "Implicitly generated list key to maintain the order of the augeas data.";
                            }
                            choice ch-config-entries {
                              mandatory true;
                              leaf source {
                                type string {
                                  pattern "[^;=# \t\n]+([^;=#\n]*[^;=# \t\n]+)*";
                                }
                                augex:data-path ".source";
                              }
                              container key {
                                augex:data-path "$$";
                                augex:value-yang-path "simple-value";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                uses export;
                              }
                              container unset {
                                augex:data-path "@unset";
                                presence "Config entry.";
                                uses var-action-list;
                              }
                              container export {
                                augex:data-path "@export";
                                presence "Config entry.";
                                uses var-action-list;
                              }
                              container builtin {
                                augex:data-path "@builtin";
                                augex:value-yang-path "shell-builtin-cmds";
                                presence "Config entry.";
                                leaf shell-builtin-cmds {
                                  mandatory true;
                                  type string {
                                    pattern "(((ulimit)|(shift))|(exit))|(:)";
                                  }
                                }
                                leaf args {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "args";
                                }
                              }
                              leaf return {
                                type union {
                                  type empty;
                                  type uint64;
                                }
                                augex:data-path "@return";
                              }
                              container condition {
                                augex:data-path "@condition";
                                augex:value-yang-path "sto-to-semicol";
                                presence "Config entry.";
                                uses type;
                              }
                              leaf eval {
                                type string {
                                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                }
                                augex:data-path "@eval";
                              }
                              container alias {
                                augex:data-path "@alias";
                                augex:value-yang-path "key";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                leaf value {
                                  mandatory true;
                                  type string {
                                    pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                  }
                                  augex:data-path "value";
                                }
                              }
                              leaf _command-ref {
                                type leafref {
                                  path "../../../../../command-list/_r-id";
                                }
                                description
                                  "Implicitly generated leaf to maintain recursive augeas data.";
                              }
                            }
                          }
                        }
                      }
                    }
                  }
                  leaf _if-ref {
                    type leafref {
                      path "../../../../if-list/_r-id";
                    }
                    description
                      "Implicitly generated leaf to maintain recursive augeas data.";
                  }
                }
              }
            }
            container select {
              augex:data-path "@select";
              augex:value-yang-path "sto-to-semicol";
              presence "Config entry.";
              leaf sto-to-semicol {
                mandatory true;
                type string {
                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                }
              }
              list ch-and-list {
                key "_id";
                ordered-by user;
                leaf _id {
                  type uint64;
                  description
                    "Implicitly generated list key to maintain the order of the augeas data.";
                }
                uses ch-and;
              }
              list config-entries {
                key "_id";
                ordered-by user;
                leaf _id {
                  type uint64;
                  description
                    "Implicitly generated list key to maintain the order of the augeas data.";
                }
                choice ch-config-entries {
                  mandatory true;
                  leaf source {
                    type string {
                      pattern "[^;=# \t\n]+([^;=#\n]*[^;=# \t\n]+)*";
                    }
                    augex:data-path ".source";
                  }
                  container key {
                    augex:data-path "$$";
                    augex:value-yang-path "simple-value";
                    presence "Config entry.";
                    leaf key {
                      mandatory true;
                      type string {
                        pattern "[-A-Za-z0-9_]+(\\[[0-9A-Za-z_,]+\\])?";
                        pattern "unset|export" {
                          modifier invert-match;
                        }
                      }
                    }
                    uses export;
                  }
                  container unset {
                    augex:data-path "@unset";
                    presence "Config entry.";
                    uses var-action-list;
                  }
                  container export {
                    augex:data-path "@export";
                    presence "Config entry.";
                    uses var-action-list;
                  }
                  container builtin {
                    augex:data-path "@builtin";
                    augex:value-yang-path "shell-builtin-cmds";
                    presence "Config entry.";
                    leaf shell-builtin-cmds {
                      mandatory true;
                      type string {
                        pattern "(((ulimit)|(shift))|(exit))|(:)";
                      }
                    }
                    leaf args {
                      type string {
                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                      }
                      augex:data-path "args";
                    }
                  }
                  leaf return {
                    type union {
                      type empty;
                      type uint64;
                    }
                    augex:data-path "@return";
                  }
                  container condition {
                    augex:data-path "@condition";
                    augex:value-yang-path "sto-to-semicol";
                    presence "Config entry.";
                    uses type;
                  }
                  leaf eval {
                    type string {
                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                    }
                    augex:data-path "@eval";
                  }
                  container alias {
                    augex:data-path "@alias";
                    augex:value-yang-path "key";
                    presence "Config entry.";
                    leaf key {
                      mandatory true;
                      type string {
                        pattern "[-A-Za-z0-9_]+(\\[[0-9A-Za-z_,]+\\])?";
                        pattern "unset|export" {
                          modifier invert-match;
                        }
                      }
                    }
                    leaf value {
                      mandatory true;
                      type string {
                        pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                      }
                      augex:data-path "value";
                    }
                  }
                  list command-list {
                    key "_r-id";
                    leaf _r-id {
                      type uint64;
                      description
                        "Implicitly generated list key to maintain the recursive augeas data.";
                    }
                    container command {
                      augex:data-path "@command";
                      augex:value-yang-path "value";
                      presence "Config entry.";
                      uses key-list;
                      leaf value {
                        mandatory true;
                        type string {
                          pattern "$?[-A-Za-z0-9_./]+";
                          pattern "exit|shift|return|ulimit|unset|export|source|\\.|if|for|select|while|until|then|else|fi|done|case|eval|alias" {
                            modifier invert-match;
                          }
                        }
                      }
                      leaf arg {
                        type string {
                          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                        }
                        augex:data-path "@arg";
                      }
                      choice ch-command {
                        container pipe {
                          augex:data-path "@pipe";
                          presence "Config entry.";
                          list config-entries {
                            key "_id";
                            ordered-by user;
                            leaf _id {
                              type uint64;
                              description
                                "Implicitly generated list key to maintain the order of the augeas data.";
                            }
                            leaf _command-ref {
                              type leafref {
                                path "../../../../../command-list/_r-id";
                              }
                              description
                                "Implicitly generated leaf to maintain recursive augeas data.";
                            }
                          }
                        }
                        container and {
                          augex:data-path "@and";
                          presence "Config entry.";
                          list config-entries {
                            key "_id";
                            ordered-by user;
                            leaf _id {
                              type uint64;
                              description
                                "Implicitly generated list key to maintain the order of the augeas data.";
                            }
                            choice ch-config-entries {
                              mandatory true;
                              leaf source {
                                type string {
                                  pattern "[^;=# \t\n]+([^;=#\n]*[^;=# \t\n]+)*";
                                }
                                augex:data-path ".source";
                              }
                              container key {
                                augex:data-path "$$";
                                augex:value-yang-path "simple-value";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                uses export;
                              }
                              container unset {
                                augex:data-path "@unset";
                                presence "Config entry.";
                                uses var-action-list;
                              }
                              container export {
                                augex:data-path "@export";
                                presence "Config entry.";
                                uses var-action-list;
                              }
                              container builtin {
                                augex:data-path "@builtin";
                                augex:value-yang-path "shell-builtin-cmds";
                                presence "Config entry.";
                                leaf shell-builtin-cmds {
                                  mandatory true;
                                  type string {
                                    pattern "(((ulimit)|(shift))|(exit))|(:)";
                                  }
                                }
                                leaf args {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "args";
                                }
                              }
                              leaf return {
                                type union {
                                  type empty;
                                  type uint64;
                                }
                                augex:data-path "@return";
                              }
                              container condition {
                                augex:data-path "@condition";
                                augex:value-yang-path "sto-to-semicol";
                                presence "Config entry.";
                                uses type;
                              }
                              leaf eval {
                                type string {
                                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                }
                                augex:data-path "@eval";
                              }
                              container alias {
                                augex:data-path "@alias";
                                augex:value-yang-path "key";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                leaf value {
                                  mandatory true;
                                  type string {
                                    pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                  }
                                  augex:data-path "value";
                                }
                              }
                              leaf _command-ref {
                                type leafref {
                                  path "../../../../../command-list/_r-id";
                                }
                                description
                                  "Implicitly generated leaf to maintain recursive augeas data.";
                              }
                            }
                          }
                        }
                        container or {
                          augex:data-path "@or";
                          presence "Config entry.";
                          list config-entries {
                            key "_id";
                            ordered-by user;
                            leaf _id {
                              type uint64;
                              description
                                "Implicitly generated list key to maintain the order of the augeas data.";
                            }
                            choice ch-config-entries {
                              mandatory true;
                              leaf source {
                                type string {
                                  pattern "[^;=# \t\n]+([^;=#\n]*[^;=# \t\n]+)*";
                                }
                                augex:data-path ".source";
                              }
                              container key {
                                augex:data-path "$$";
                                augex:value-yang-path "simple-value";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                uses export;
                              }
                              container unset {
                                augex:data-path "@unset";
                                presence "Config entry.";
                                uses var-action-list;
                              }
                              container export {
                                augex:data-path "@export";
                                presence "Config entry.";
                                uses var-action-list;
                              }
                              container builtin {
                                augex:data-path "@builtin";
                                augex:value-yang-path "shell-builtin-cmds";
                                presence "Config entry.";
                                leaf shell-builtin-cmds {
                                  mandatory true;
                                  type string {
                                    pattern "(((ulimit)|(shift))|(exit))|(:)";
                                  }
                                }
                                leaf args {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "args";
                                }
                              }
                              leaf return {
                                type union {
                                  type empty;
                                  type uint64;
                                }
                                augex:data-path "@return";
                              }
                              container condition {
                                augex:data-path "@condition";
                                augex:value-yang-path "sto-to-semicol";
                                presence "Config entry.";
                                uses type;
                              }
                              leaf eval {
                                type string {
                                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                }
                                augex:data-path "@eval";
                              }
                              container alias {
                                augex:data-path "@alias";
                                augex:value-yang-path "key";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                leaf value {
                                  mandatory true;
                                  type string {
                                    pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                  }
                                  augex:data-path "value";
                                }
                              }
                              leaf _command-ref {
                                type leafref {
                                  path "../../../../../command-list/_r-id";
                                }
                                description
                                  "Implicitly generated leaf to maintain recursive augeas data.";
                              }
                            }
                          }
                        }
                      }
                    }
                  }
                  leaf _if-ref {
                    type leafref {
                      path "../../../../if-list/_r-id";
                    }
                    description
                      "Implicitly generated leaf to maintain recursive augeas data.";
                  }
                }
              }
            }
            container while {
              augex:data-path "@while";
              augex:value-yang-path "sto-to-semicol";
              presence "Config entry.";
              leaf sto-to-semicol {
                mandatory true;
                type string {
                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                }
              }
              list ch-and-list {
                key "_id";
                ordered-by user;
                leaf _id {
                  type uint64;
                  description
                    "Implicitly generated list key to maintain the order of the augeas data.";
                }
                uses ch-and;
              }
              list config-entries {
                key "_id";
                ordered-by user;
                leaf _id {
                  type uint64;
                  description
                    "Implicitly generated list key to maintain the order of the augeas data.";
                }
                choice ch-config-entries {
                  mandatory true;
                  leaf source {
                    type string {
                      pattern "[^;=# \t\n]+([^;=#\n]*[^;=# \t\n]+)*";
                    }
                    augex:data-path ".source";
                  }
                  container key {
                    augex:data-path "$$";
                    augex:value-yang-path "simple-value";
                    presence "Config entry.";
                    leaf key {
                      mandatory true;
                      type string {
                        pattern "[-A-Za-z0-9_]+(\\[[0-9A-Za-z_,]+\\])?";
                        pattern "unset|export" {
                          modifier invert-match;
                        }
                      }
                    }
                    uses export;
                  }
                  container unset {
                    augex:data-path "@unset";
                    presence "Config entry.";
                    uses var-action-list;
                  }
                  container export {
                    augex:data-path "@export";
                    presence "Config entry.";
                    uses var-action-list;
                  }
                  container builtin {
                    augex:data-path "@builtin";
                    augex:value-yang-path "shell-builtin-cmds";
                    presence "Config entry.";
                    leaf shell-builtin-cmds {
                      mandatory true;
                      type string {
                        pattern "(((ulimit)|(shift))|(exit))|(:)";
                      }
                    }
                    leaf args {
                      type string {
                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                      }
                      augex:data-path "args";
                    }
                  }
                  leaf return {
                    type union {
                      type empty;
                      type uint64;
                    }
                    augex:data-path "@return";
                  }
                  container condition {
                    augex:data-path "@condition";
                    augex:value-yang-path "sto-to-semicol";
                    presence "Config entry.";
                    uses type;
                  }
                  leaf eval {
                    type string {
                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                    }
                    augex:data-path "@eval";
                  }
                  container alias {
                    augex:data-path "@alias";
                    augex:value-yang-path "key";
                    presence "Config entry.";
                    leaf key {
                      mandatory true;
                      type string {
                        pattern "[-A-Za-z0-9_]+(\\[[0-9A-Za-z_,]+\\])?";
                        pattern "unset|export" {
                          modifier invert-match;
                        }
                      }
                    }
                    leaf value {
                      mandatory true;
                      type string {
                        pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                      }
                      augex:data-path "value";
                    }
                  }
                  list command-list {
                    key "_r-id";
                    leaf _r-id {
                      type uint64;
                      description
                        "Implicitly generated list key to maintain the recursive augeas data.";
                    }
                    container command {
                      augex:data-path "@command";
                      augex:value-yang-path "value";
                      presence "Config entry.";
                      uses key-list;
                      leaf value {
                        mandatory true;
                        type string {
                          pattern "$?[-A-Za-z0-9_./]+";
                          pattern "exit|shift|return|ulimit|unset|export|source|\\.|if|for|select|while|until|then|else|fi|done|case|eval|alias" {
                            modifier invert-match;
                          }
                        }
                      }
                      leaf arg {
                        type string {
                          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                        }
                        augex:data-path "@arg";
                      }
                      choice ch-command {
                        container pipe {
                          augex:data-path "@pipe";
                          presence "Config entry.";
                          list config-entries {
                            key "_id";
                            ordered-by user;
                            leaf _id {
                              type uint64;
                              description
                                "Implicitly generated list key to maintain the order of the augeas data.";
                            }
                            leaf _command-ref {
                              type leafref {
                                path "../../../../../command-list/_r-id";
                              }
                              description
                                "Implicitly generated leaf to maintain recursive augeas data.";
                            }
                          }
                        }
                        container and {
                          augex:data-path "@and";
                          presence "Config entry.";
                          list config-entries {
                            key "_id";
                            ordered-by user;
                            leaf _id {
                              type uint64;
                              description
                                "Implicitly generated list key to maintain the order of the augeas data.";
                            }
                            choice ch-config-entries {
                              mandatory true;
                              leaf source {
                                type string {
                                  pattern "[^;=# \t\n]+([^;=#\n]*[^;=# \t\n]+)*";
                                }
                                augex:data-path ".source";
                              }
                              container key {
                                augex:data-path "$$";
                                augex:value-yang-path "simple-value";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                uses export;
                              }
                              container unset {
                                augex:data-path "@unset";
                                presence "Config entry.";
                                uses var-action-list;
                              }
                              container export {
                                augex:data-path "@export";
                                presence "Config entry.";
                                uses var-action-list;
                              }
                              container builtin {
                                augex:data-path "@builtin";
                                augex:value-yang-path "shell-builtin-cmds";
                                presence "Config entry.";
                                leaf shell-builtin-cmds {
                                  mandatory true;
                                  type string {
                                    pattern "(((ulimit)|(shift))|(exit))|(:)";
                                  }
                                }
                                leaf args {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "args";
                                }
                              }
                              leaf return {
                                type union {
                                  type empty;
                                  type uint64;
                                }
                                augex:data-path "@return";
                              }
                              container condition {
                                augex:data-path "@condition";
                                augex:value-yang-path "sto-to-semicol";
                                presence "Config entry.";
                                uses type;
                              }
                              leaf eval {
                                type string {
                                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                }
                                augex:data-path "@eval";
                              }
                              container alias {
                                augex:data-path "@alias";
                                augex:value-yang-path "key";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                leaf value {
                                  mandatory true;
                                  type string {
                                    pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                  }
                                  augex:data-path "value";
                                }
                              }
                              leaf _command-ref {
                                type leafref {
                                  path "../../../../../command-list/_r-id";
                                }
                                description
                                  "Implicitly generated leaf to maintain recursive augeas data.";
                              }
                            }
                          }
                        }
                        container or {
                          augex:data-path "@or";
                          presence "Config entry.";
                          list config-entries {
                            key "_id";
                            ordered-by user;
                            leaf _id {
                              type uint64;
                              description
                                "Implicitly generated list key to maintain the order of the augeas data.";
                            }
                            choice ch-config-entries {
                              mandatory true;
                              leaf source {
                                type string {
                                  pattern "[^;=# \t\n]+([^;=#\n]*[^;=# \t\n]+)*";
                                }
                                augex:data-path ".source";
                              }
                              container key {
                                augex:data-path "$$";
                                augex:value-yang-path "simple-value";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                uses export;
                              }
                              container unset {
                                augex:data-path "@unset";
                                presence "Config entry.";
                                uses var-action-list;
                              }
                              container export {
                                augex:data-path "@export";
                                presence "Config entry.";
                                uses var-action-list;
                              }
                              container builtin {
                                augex:data-path "@builtin";
                                augex:value-yang-path "shell-builtin-cmds";
                                presence "Config entry.";
                                leaf shell-builtin-cmds {
                                  mandatory true;
                                  type string {
                                    pattern "(((ulimit)|(shift))|(exit))|(:)";
                                  }
                                }
                                leaf args {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "args";
                                }
                              }
                              leaf return {
                                type union {
                                  type empty;
                                  type uint64;
                                }
                                augex:data-path "@return";
                              }
                              container condition {
                                augex:data-path "@condition";
                                augex:value-yang-path "sto-to-semicol";
                                presence "Config entry.";
                                uses type;
                              }
                              leaf eval {
                                type string {
                                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                }
                                augex:data-path "@eval";
                              }
                              container alias {
                                augex:data-path "@alias";
                                augex:value-yang-path "key";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                leaf value {
                                  mandatory true;
                                  type string {
                                    pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                  }
                                  augex:data-path "value";
                                }
                              }
                              leaf _command-ref {
                                type leafref {
                                  path "../../../../../command-list/_r-id";
                                }
                                description
                                  "Implicitly generated leaf to maintain recursive augeas data.";
                              }
                            }
                          }
                        }
                      }
                    }
                  }
                  leaf _if-ref {
                    type leafref {
                      path "../../../../if-list/_r-id";
                    }
                    description
                      "Implicitly generated leaf to maintain recursive augeas data.";
                  }
                }
              }
            }
            container until {
              augex:data-path "@until";
              augex:value-yang-path "sto-to-semicol";
              presence "Config entry.";
              leaf sto-to-semicol {
                mandatory true;
                type string {
                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                }
              }
              list ch-and-list {
                key "_id";
                ordered-by user;
                leaf _id {
                  type uint64;
                  description
                    "Implicitly generated list key to maintain the order of the augeas data.";
                }
                uses ch-and;
              }
              list config-entries {
                key "_id";
                ordered-by user;
                leaf _id {
                  type uint64;
                  description
                    "Implicitly generated list key to maintain the order of the augeas data.";
                }
                choice ch-config-entries {
                  mandatory true;
                  leaf source {
                    type string {
                      pattern "[^;=# \t\n]+([^;=#\n]*[^;=# \t\n]+)*";
                    }
                    augex:data-path ".source";
                  }
                  container key {
                    augex:data-path "$$";
                    augex:value-yang-path "simple-value";
                    presence "Config entry.";
                    leaf key {
                      mandatory true;
                      type string {
                        pattern "[-A-Za-z0-9_]+(\\[[0-9A-Za-z_,]+\\])?";
                        pattern "unset|export" {
                          modifier invert-match;
                        }
                      }
                    }
                    uses export;
                  }
                  container unset {
                    augex:data-path "@unset";
                    presence "Config entry.";
                    uses var-action-list;
                  }
                  container export {
                    augex:data-path "@export";
                    presence "Config entry.";
                    uses var-action-list;
                  }
                  container builtin {
                    augex:data-path "@builtin";
                    augex:value-yang-path "shell-builtin-cmds";
                    presence "Config entry.";
                    leaf shell-builtin-cmds {
                      mandatory true;
                      type string {
                        pattern "(((ulimit)|(shift))|(exit))|(:)";
                      }
                    }
                    leaf args {
                      type string {
                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                      }
                      augex:data-path "args";
                    }
                  }
                  leaf return {
                    type union {
                      type empty;
                      type uint64;
                    }
                    augex:data-path "@return";
                  }
                  container condition {
                    augex:data-path "@condition";
                    augex:value-yang-path "sto-to-semicol";
                    presence "Config entry.";
                    uses type;
                  }
                  leaf eval {
                    type string {
                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                    }
                    augex:data-path "@eval";
                  }
                  container alias {
                    augex:data-path "@alias";
                    augex:value-yang-path "key";
                    presence "Config entry.";
                    leaf key {
                      mandatory true;
                      type string {
                        pattern "[-A-Za-z0-9_]+(\\[[0-9A-Za-z_,]+\\])?";
                        pattern "unset|export" {
                          modifier invert-match;
                        }
                      }
                    }
                    leaf value {
                      mandatory true;
                      type string {
                        pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                      }
                      augex:data-path "value";
                    }
                  }
                  list command-list {
                    key "_r-id";
                    leaf _r-id {
                      type uint64;
                      description
                        "Implicitly generated list key to maintain the recursive augeas data.";
                    }
                    container command {
                      augex:data-path "@command";
                      augex:value-yang-path "value";
                      presence "Config entry.";
                      uses key-list;
                      leaf value {
                        mandatory true;
                        type string {
                          pattern "$?[-A-Za-z0-9_./]+";
                          pattern "exit|shift|return|ulimit|unset|export|source|\\.|if|for|select|while|until|then|else|fi|done|case|eval|alias" {
                            modifier invert-match;
                          }
                        }
                      }
                      leaf arg {
                        type string {
                          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                        }
                        augex:data-path "@arg";
                      }
                      choice ch-command {
                        container pipe {
                          augex:data-path "@pipe";
                          presence "Config entry.";
                          list config-entries {
                            key "_id";
                            ordered-by user;
                            leaf _id {
                              type uint64;
                              description
                                "Implicitly generated list key to maintain the order of the augeas data.";
                            }
                            leaf _command-ref {
                              type leafref {
                                path "../../../../../command-list/_r-id";
                              }
                              description
                                "Implicitly generated leaf to maintain recursive augeas data.";
                            }
                          }
                        }
                        container and {
                          augex:data-path "@and";
                          presence "Config entry.";
                          list config-entries {
                            key "_id";
                            ordered-by user;
                            leaf _id {
                              type uint64;
                              description
                                "Implicitly generated list key to maintain the order of the augeas data.";
                            }
                            choice ch-config-entries {
                              mandatory true;
                              leaf source {
                                type string {
                                  pattern "[^;=# \t\n]+([^;=#\n]*[^;=# \t\n]+)*";
                                }
                                augex:data-path ".source";
                              }
                              container key {
                                augex:data-path "$$";
                                augex:value-yang-path "simple-value";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                uses export;
                              }
                              container unset {
                                augex:data-path "@unset";
                                presence "Config entry.";
                                uses var-action-list;
                              }
                              container export {
                                augex:data-path "@export";
                                presence "Config entry.";
                                uses var-action-list;
                              }
                              container builtin {
                                augex:data-path "@builtin";
                                augex:value-yang-path "shell-builtin-cmds";
                                presence "Config entry.";
                                leaf shell-builtin-cmds {
                                  mandatory true;
                                  type string {
                                    pattern "(((ulimit)|(shift))|(exit))|(:)";
                                  }
                                }
                                leaf args {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "args";
                                }
                              }
                              leaf return {
                                type union {
                                  type empty;
                                  type uint64;
                                }
                                augex:data-path "@return";
                              }
                              container condition {
                                augex:data-path "@condition";
                                augex:value-yang-path "sto-to-semicol";
                                presence "Config entry.";
                                uses type;
                              }
                              leaf eval {
                                type string {
                                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                }
                                augex:data-path "@eval";
                              }
                              container alias {
                                augex:data-path "@alias";
                                augex:value-yang-path "key";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                leaf value {
                                  mandatory true;
                                  type string {
                                    pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                  }
                                  augex:data-path "value";
                                }
                              }
                              leaf _command-ref {
                                type leafref {
                                  path "../../../../../command-list/_r-id";
                                }
                                description
                                  "Implicitly generated leaf to maintain recursive augeas data.";
                              }
                            }
                          }
                        }
                        container or {
                          augex:data-path "@or";
                          presence "Config entry.";
                          list config-entries {
                            key "_id";
                            ordered-by user;
                            leaf _id {
                              type uint64;
                              description
                                "Implicitly generated list key to maintain the order of the augeas data.";
                            }
                            choice ch-config-entries {
                              mandatory true;
                              leaf source {
                                type string {
                                  pattern "[^;=# \t\n]+([^;=#\n]*[^;=# \t\n]+)*";
                                }
                                augex:data-path ".source";
                              }
                              container key {
                                augex:data-path "$$";
                                augex:value-yang-path "simple-value";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                uses export;
                              }
                              container unset {
                                augex:data-path "@unset";
                                presence "Config entry.";
                                uses var-action-list;
                              }
                              container export {
                                augex:data-path "@export";
                                presence "Config entry.";
                                uses var-action-list;
                              }
                              container builtin {
                                augex:data-path "@builtin";
                                augex:value-yang-path "shell-builtin-cmds";
                                presence "Config entry.";
                                leaf shell-builtin-cmds {
                                  mandatory true;
                                  type string {
                                    pattern "(((ulimit)|(shift))|(exit))|(:)";
                                  }
                                }
                                leaf args {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "args";
                                }
                              }
                              leaf return {
                                type union {
                                  type empty;
                                  type uint64;
                                }
                                augex:data-path "@return";
                              }
                              container condition {
                                augex:data-path "@condition";
                                augex:value-yang-path "sto-to-semicol";
                                presence "Config entry.";
                                uses type;
                              }
                              leaf eval {
                                type string {
                                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                }
                                augex:data-path "@eval";
                              }
                              container alias {
                                augex:data-path "@alias";
                                augex:value-yang-path "key";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                leaf value {
                                  mandatory true;
                                  type string {
                                    pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                  }
                                  augex:data-path "value";
                                }
                              }
                              leaf _command-ref {
                                type leafref {
                                  path "../../../../../command-list/_r-id";
                                }
                                description
                                  "Implicitly generated leaf to maintain recursive augeas data.";
                              }
                            }
                          }
                        }
                      }
                    }
                  }
                  leaf _if-ref {
                    type leafref {
                      path "../../../../if-list/_r-id";
                    }
                    description
                      "Implicitly generated leaf to maintain recursive augeas data.";
                  }
                }
              }
            }
            container case {
              augex:data-path "@case";
              augex:value-yang-path "value";
              presence "Config entry.";
              leaf value {
                mandatory true;
                type string {
                  pattern "(([^`;()'\"&|\n\\\\# \t]#*|\\\\.)+)|(((\")(([^`;()'\"&|\n\\\\# \t]#*|\\\\.)+))(\"))";
                }
              }
              list case-entry-list {
                key "_id";
                ordered-by user;
                leaf _id {
                  type uint64;
                  description
                    "Implicitly generated list key to maintain the order of the augeas data.";
                }
                container case-entry {
                  augex:data-path "@case_entry";
                  presence "Config entry.";
                  list pattern-list {
                    key "_id";
                    min-elements 1;
                    ordered-by user;
                    leaf _id {
                      type uint64;
                      description
                        "Implicitly generated list key to maintain the order of the augeas data.";
                    }
                    leaf pattern {
                      mandatory true;
                      type string {
                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                      }
                      augex:data-path "@pattern";
                    }
                  }
                  list config-entries {
                    key "_id";
                    ordered-by user;
                    leaf _id {
                      type uint64;
                      description
                        "Implicitly generated list key to maintain the order of the augeas data.";
                    }
                    choice ch-config-entries {
                      mandatory true;
                      leaf source {
                        type string {
                          pattern "[^;=# \t\n]+([^;=#\n]*[^;=# \t\n]+)*";
                        }
                        augex:data-path ".source";
                      }
                      container key {
                        augex:data-path "$$";
                        augex:value-yang-path "simple-value";
                        presence "Config entry.";
                        leaf key {
                          mandatory true;
                          type string {
                            pattern "[-A-Za-z0-9_]+(\\[[0-9A-Za-z_,]+\\])?";
                            pattern "unset|export" {
                              modifier invert-match;
                            }
                          }
                        }
                        uses export;
                      }
                      container unset {
                        augex:data-path "@unset";
                        presence "Config entry.";
                        uses var-action-list;
                      }
                      container export {
                        augex:data-path "@export";
                        presence "Config entry.";
                        uses var-action-list;
                      }
                      container builtin {
                        augex:data-path "@builtin";
                        augex:value-yang-path "shell-builtin-cmds";
                        presence "Config entry.";
                        leaf shell-builtin-cmds {
                          mandatory true;
                          type string {
                            pattern "(((ulimit)|(shift))|(exit))|(:)";
                          }
                        }
                        leaf args {
                          type string {
                            pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                          }
                          augex:data-path "args";
                        }
                      }
                      leaf return {
                        type union {
                          type empty;
                          type uint64;
                        }
                        augex:data-path "@return";
                      }
                      container condition {
                        augex:data-path "@condition";
                        augex:value-yang-path "sto-to-semicol";
                        presence "Config entry.";
                        uses type;
                      }
                      leaf eval {
                        type string {
                          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                        }
                        augex:data-path "@eval";
                      }
                      container alias {
                        augex:data-path "@alias";
                        augex:value-yang-path "key";
                        presence "Config entry.";
                        leaf key {
                          mandatory true;
                          type string {
                            pattern "[-A-Za-z0-9_]+(\\[[0-9A-Za-z_,]+\\])?";
                            pattern "unset|export" {
                              modifier invert-match;
                            }
                          }
                        }
                        leaf value {
                          mandatory true;
                          type string {
                            pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                          }
                          augex:data-path "value";
                        }
                      }
                      list command-list {
                        key "_r-id";
                        leaf _r-id {
                          type uint64;
                          description
                            "Implicitly generated list key to maintain the recursive augeas data.";
                        }
                        container command {
                          augex:data-path "@command";
                          augex:value-yang-path "value";
                          presence "Config entry.";
                          uses key-list;
                          leaf value {
                            mandatory true;
                            type string {
                              pattern "$?[-A-Za-z0-9_./]+";
                              pattern "exit|shift|return|ulimit|unset|export|source|\\.|if|for|select|while|until|then|else|fi|done|case|eval|alias" {
                                modifier invert-match;
                              }
                            }
                          }
                          leaf arg {
                            type string {
                              pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                            }
                            augex:data-path "@arg";
                          }
                          choice ch-command {
                            container pipe {
                              augex:data-path "@pipe";
                              presence "Config entry.";
                              list config-entries {
                                key "_id";
                                ordered-by user;
                                leaf _id {
                                  type uint64;
                                  description
                                    "Implicitly generated list key to maintain the order of the augeas data.";
                                }
                                leaf _command-ref {
                                  type leafref {
                                    path "../../../../../command-list/_r-id";
                                  }
                                  description
                                    "Implicitly generated leaf to maintain recursive augeas data.";
                                }
                              }
                            }
                            container and {
                              augex:data-path "@and";
                              presence "Config entry.";
                              list config-entries {
                                key "_id";
                                ordered-by user;
                                leaf _id {
                                  type uint64;
                                  description
                                    "Implicitly generated list key to maintain the order of the augeas data.";
                                }
                                choice ch-config-entries {
                                  mandatory true;
                                  leaf source {
                                    type string {
                                      pattern "[^;=# \t\n]+([^;=#\n]*[^;=# \t\n]+)*";
                                    }
                                    augex:data-path ".source";
                                  }
                                  container key {
                                    augex:data-path "$$";
                                    augex:value-yang-path "simple-value";
                                    presence "Config entry.";
                                    leaf key {
                                      mandatory true;
                                      type string {
                                        pattern "[-A-Za-z0-9_]+(\\[[0-9A-Za-z_,]+\\])?";
                                        pattern "unset|export" {
                                          modifier invert-match;
                                        }
                                      }
                                    }
                                    uses export;
                                  }
                                  container unset {
                                    augex:data-path "@unset";
                                    presence "Config entry.";
                                    uses var-action-list;
                                  }
                                  container export {
                                    augex:data-path "@export";
                                    presence "Config entry.";
                                    uses var-action-list;
                                  }
                                  container builtin {
                                    augex:data-path "@builtin";
                                    augex:value-yang-path "shell-builtin-cmds";
                                    presence "Config entry.";
                                    leaf shell-builtin-cmds {
                                      mandatory true;
                                      type string {
                                        pattern "(((ulimit)|(shift))|(exit))|(:)";
                                      }
                                    }
                                    leaf args {
                                      type string {
                                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                      }
                                      augex:data-path "args";
                                    }
                                  }
                                  leaf return {
                                    type union {
                                      type empty;
                                      type uint64;
                                    }
                                    augex:data-path "@return";
                                  }
                                  container condition {
                                    augex:data-path "@condition";
                                    augex:value-yang-path "sto-to-semicol";
                                    presence "Config entry.";
                                    uses type;
                                  }
                                  leaf eval {
                                    type string {
                                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                    }
                                    augex:data-path "@eval";
                                  }
                                  container alias {
                                    augex:data-path "@alias";
                                    augex:value-yang-path "key";
                                    presence "Config entry.";
                                    leaf key {
                                      mandatory true;
                                      type string {
                                        pattern "[-A-Za-z0-9_]+(\\[[0-9A-Za-z_,]+\\])?";
                                        pattern "unset|export" {
                                          modifier invert-match;
                                        }
                                      }
                                    }
                                    leaf value {
                                      mandatory true;
                                      type string {
                                        pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                      }
                                      augex:data-path "value";
                                    }
                                  }
                                  leaf _command-ref {
                                    type leafref {
                                      path "../../../../../command-list/_r-id";
                                    }
                                    description
                                      "Implicitly generated leaf to maintain recursive augeas data.";
                                  }
                                }
                              }
                            }
                            container or {
                              augex:data-path "@or";
                              presence "Config entry.";
                              list config-entries {
                                key "_id";
                                ordered-by user;
                                leaf _id {
                                  type uint64;
                                  description
                                    "Implicitly generated list key to maintain the order of the augeas data.";
                                }
                                choice ch-config-entries {
                                  mandatory true;
                                  leaf source {
                                    type string {
                                      pattern "[^;=# \t\n]+([^;=#\n]*[^;=# \t\n]+)*";
                                    }
                                    augex:data-path ".source";
                                  }
                                  container key {
                                    augex:data-path "$$";
                                    augex:value-yang-path "simple-value";
                                    presence "Config entry.";
                                    leaf key {
                                      mandatory true;
                                      type string {
                                        pattern "[-A-Za-z0-9_]+(\\[[0-9A-Za-z_,]+\\])?";
                                        pattern "unset|export" {
                                          modifier invert-match;
                                        }
                                      }
                                    }
                                    uses export;
                                  }
                                  container unset {
                                    augex:data-path "@unset";
                                    presence "Config entry.";
                                    uses var-action-list;
                                  }
                                  container export {
                                    augex:data-path "@export";
                                    presence "Config entry.";
                                    uses var-action-list;
                                  }
                                  container builtin {
                                    augex:data-path "@builtin";
                                    augex:value-yang-path "shell-builtin-cmds";
                                    presence "Config entry.";
                                    leaf shell-builtin-cmds {
                                      mandatory true;
                                      type string {
                                        pattern "(((ulimit)|(shift))|(exit))|(:)";
                                      }
                                    }
                                    leaf args {
                                      type string {
                                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                      }
                                      augex:data-path "args";
                                    }
                                  }
                                  leaf return {
                                    type union {
                                      type empty;
                                      type uint64;
                                    }
                                    augex:data-path "@return";
                                  }
                                  container condition {
                                    augex:data-path "@condition";
                                    augex:value-yang-path "sto-to-semicol";
                                    presence "Config entry.";
                                    uses type;
                                  }
                                  leaf eval {
                                    type string {
                                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                    }
                                    augex:data-path "@eval";
                                  }
                                  container alias {
                                    augex:data-path "@alias";
                                    augex:value-yang-path "key";
                                    presence "Config entry.";
                                    leaf key {
                                      mandatory true;
                                      type string {
                                        pattern "[-A-Za-z0-9_]+(\\[[0-9A-Za-z_,]+\\])?";
                                        pattern "unset|export" {
                                          modifier invert-match;
                                        }
                                      }
                                    }
                                    leaf value {
                                      mandatory true;
                                      type string {
                                        pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                      }
                                      augex:data-path "value";
                                    }
                                  }
                                  leaf _command-ref {
                                    type leafref {
                                      path "../../../../../command-list/_r-id";
                                    }
                                    description
                                      "Implicitly generated leaf to maintain recursive augeas data.";
                                  }
                                }
                              }
                            }
                          }
                        }
                      }
                      leaf _if-ref {
                        type leafref {
                          path "../../../../../../if-list/_r-id";
                        }
                        description
                          "Implicitly generated leaf to maintain recursive augeas data.";
                      }
                    }
                  }
                  choice ch-case-entry {
                    leaf source {
                      type string {
                        pattern "[^;=# \t\n]+([^;=#\n]*[^;=# \t\n]+)*";
                      }
                      augex:data-path ".source";
                    }
                    container key {
                      augex:data-path "$$";
                      augex:value-yang-path "simple-value";
                      presence "Config entry.";
                      leaf key {
                        mandatory true;
                        type string {
                          pattern "[-A-Za-z0-9_]+(\\[[0-9A-Za-z_,]+\\])?";
                          pattern "unset|export" {
                            modifier invert-match;
                          }
                        }
                      }
                      uses export;
                    }
                    container unset {
                      augex:data-path "@unset";
                      presence "Config entry.";
                      uses var-action-list;
                    }
                    container export {
                      augex:data-path "@export";
                      presence "Config entry.";
                      uses var-action-list;
                    }
                    container builtin {
                      augex:data-path "@builtin";
                      augex:value-yang-path "shell-builtin-cmds";
                      presence "Config entry.";
                      leaf shell-builtin-cmds {
                        mandatory true;
                        type string {
                          pattern "(((ulimit)|(shift))|(exit))|(:)";
                        }
                      }
                      leaf args {
                        type string {
                          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                        }
                        augex:data-path "args";
                      }
                    }
                    leaf return {
                      type union {
                        type empty;
                        type uint64;
                      }
                      augex:data-path "@return";
                    }
                    container condition {
                      augex:data-path "@condition";
                      augex:value-yang-path "sto-to-semicol";
                      presence "Config entry.";
                      uses type;
                    }
                    leaf eval {
                      type string {
                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                      }
                      augex:data-path "@eval";
                    }
                    container alias {
                      augex:data-path "@alias";
                      augex:value-yang-path "key";
                      presence "Config entry.";
                      leaf key {
                        mandatory true;
                        type string {
                          pattern "[-A-Za-z0-9_]+(\\[[0-9A-Za-z_,]+\\])?";
                          pattern "unset|export" {
                            modifier invert-match;
                          }
                        }
                      }
                      leaf value {
                        mandatory true;
                        type string {
                          pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                        }
                        augex:data-path "value";
                      }
                    }
                    list command-list {
                      key "_r-id";
                      leaf _r-id {
                        type uint64;
                        description
                          "Implicitly generated list key to maintain the recursive augeas data.";
                      }
                      container command {
                        augex:data-path "@command";
                        augex:value-yang-path "value";
                        presence "Config entry.";
                        uses key-list;
                        leaf value {
                          mandatory true;
                          type string {
                            pattern "$?[-A-Za-z0-9_./]+";
                            pattern "exit|shift|return|ulimit|unset|export|source|\\.|if|for|select|while|until|then|else|fi|done|case|eval|alias" {
                              modifier invert-match;
                            }
                          }
                        }
                        leaf arg {
                          type string {
                            pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                          }
                          augex:data-path "@arg";
                        }
                        choice ch-command {
                          container pipe {
                            augex:data-path "@pipe";
                            presence "Config entry.";
                            list config-entries {
                              key "_id";
                              ordered-by user;
                              leaf _id {
                                type uint64;
                                description
                                  "Implicitly generated list key to maintain the order of the augeas data.";
                              }
                              leaf _command-ref {
                                type leafref {
                                  path "../../../../../command-list/_r-id";
                                }
                                description
                                  "Implicitly generated leaf to maintain recursive augeas data.";
                              }
                            }
                          }
                          container and {
                            augex:data-path "@and";
                            presence "Config entry.";
                            list config-entries {
                              key "_id";
                              ordered-by user;
                              leaf _id {
                                type uint64;
                                description
                                  "Implicitly generated list key to maintain the order of the augeas data.";
                              }
                              choice ch-config-entries {
                                mandatory true;
                                leaf source {
                                  type string {
                                    pattern "[^;=# \t\n]+([^;=#\n]*[^;=# \t\n]+)*";
                                  }
                                  augex:data-path ".source";
                                }
                                container key {
                                  augex:data-path "$$";
                                  augex:value-yang-path "simple-value";
                                  presence "Config entry.";
                                  leaf key {
                                    mandatory true;
                                    type string {
                                      pattern "[-A-Za-z0-9_]+(\\[[0-9A-Za-z_,]+\\])?";
                                      pattern "unset|export" {
                                        modifier invert-match;
                                      }
                                    }
                                  }
                                  uses export;
                                }
                                container unset {
                                  augex:data-path "@unset";
                                  presence "Config entry.";
                                  uses var-action-list;
                                }
                                container export {
                                  augex:data-path "@export";
                                  presence "Config entry.";
                                  uses var-action-list;
                                }
                                container builtin {
                                  augex:data-path "@builtin";
                                  augex:value-yang-path "shell-builtin-cmds";
                                  presence "Config entry.";
                                  leaf shell-builtin-cmds {
                                    mandatory true;
                                    type string {
                                      pattern "(((ulimit)|(shift))|(exit))|(:)";
                                    }
                                  }
                                  leaf args {
                                    type string {
                                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                    }
                                    augex:data-path "args";
                                  }
                                }
                                leaf return {
                                  type union {
                                    type empty;
                                    type uint64;
                                  }
                                  augex:data-path "@return";
                                }
                                container condition {
                                  augex:data-path "@condition";
                                  augex:value-yang-path "sto-to-semicol";
                                  presence "Config entry.";
                                  uses type;
                                }
                                leaf eval {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "@eval";
                                }
                                container alias {
                                  augex:data-path "@alias";
                                  augex:value-yang-path "key";
                                  presence "Config entry.";
                                  leaf key {
                                    mandatory true;
                                    type string {
                                      pattern "[-A-Za-z0-9_]+(\\[[0-9A-Za-z_,]+\\])?";
                                      pattern "unset|export" {
                                        modifier invert-match;
                                      }
                                    }
                                  }
                                  leaf value {
                                    mandatory true;
                                    type string {
                                      pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                    }
                                    augex:data-path "value";
                                  }
                                }
                                leaf _command-ref {
                                  type leafref {
                                    path "../../../../../command-list/_r-id";
                                  }
                                  description
                                    "Implicitly generated leaf to maintain recursive augeas data.";
                                }
                              }
                            }
                          }
                          container or {
                            augex:data-path "@or";
                            presence "Config entry.";
                            list config-entries {
                              key "_id";
                              ordered-by user;
                              leaf _id {
                                type uint64;
                                description
                                  "Implicitly generated list key to maintain the order of the augeas data.";
                              }
                              choice ch-config-entries {
                                mandatory true;
                                leaf source {
                                  type string {
                                    pattern "[^;=# \t\n]+([^;=#\n]*[^;=# \t\n]+)*";
                                  }
                                  augex:data-path ".source";
                                }
                                container key {
                                  augex:data-path "$$";
                                  augex:value-yang-path "simple-value";
                                  presence "Config entry.";
                                  leaf key {
                                    mandatory true;
                                    type string {
                                      pattern "[-A-Za-z0-9_]+(\\[[0-9A-Za-z_,]+\\])?";
                                      pattern "unset|export" {
                                        modifier invert-match;
                                      }
                                    }
                                  }
                                  uses export;
                                }
                                container unset {
                                  augex:data-path "@unset";
                                  presence "Config entry.";
                                  uses var-action-list;
                                }
                                container export {
                                  augex:data-path "@export";
                                  presence "Config entry.";
                                  uses var-action-list;
                                }
                                container builtin {
                                  augex:data-path "@builtin";
                                  augex:value-yang-path "shell-builtin-cmds";
                                  presence "Config entry.";
                                  leaf shell-builtin-cmds {
                                    mandatory true;
                                    type string {
                                      pattern "(((ulimit)|(shift))|(exit))|(:)";
                                    }
                                  }
                                  leaf args {
                                    type string {
                                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                    }
                                    augex:data-path "args";
                                  }
                                }
                                leaf return {
                                  type union {
                                    type empty;
                                    type uint64;
                                  }
                                  augex:data-path "@return";
                                }
                                container condition {
                                  augex:data-path "@condition";
                                  augex:value-yang-path "sto-to-semicol";
                                  presence "Config entry.";
                                  uses type;
                                }
                                leaf eval {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "@eval";
                                }
                                container alias {
                                  augex:data-path "@alias";
                                  augex:value-yang-path "key";
                                  presence "Config entry.";
                                  leaf key {
                                    mandatory true;
                                    type string {
                                      pattern "[-A-Za-z0-9_]+(\\[[0-9A-Za-z_,]+\\])?";
                                      pattern "unset|export" {
                                        modifier invert-match;
                                      }
                                    }
                                  }
                                  leaf value {
                                    mandatory true;
                                    type string {
                                      pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                    }
                                    augex:data-path "value";
                                  }
                                }
                                leaf _command-ref {
                                  type leafref {
                                    path "../../../../../command-list/_r-id";
                                  }
                                  description
                                    "Implicitly generated leaf to maintain recursive augeas data.";
                                }
                              }
                            }
                          }
                        }
                      }
                    }
                  }
                }
              }
            }
            container function {
              augex:data-path "@function";
              augex:value-yang-path "word";
              presence "Config entry.";
              leaf word {
                mandatory true;
                type string {
                  pattern "[A-Za-z0-9_.-]+";
                }
              }
              list config-entries {
                key "_id";
                ordered-by user;
                leaf _id {
                  type uint64;
                  description
                    "Implicitly generated list key to maintain the order of the augeas data.";
                }
                choice ch-config-entries {
                  mandatory true;
                  leaf source {
                    type string {
                      pattern "[^;=# \t\n]+([^;=#\n]*[^;=# \t\n]+)*";
                    }
                    augex:data-path ".source";
                  }
                  container key {
                    augex:data-path "$$";
                    augex:value-yang-path "simple-value";
                    presence "Config entry.";
                    leaf key {
                      mandatory true;
                      type string {
                        pattern "[-A-Za-z0-9_]+(\\[[0-9A-Za-z_,]+\\])?";
                        pattern "unset|export" {
                          modifier invert-match;
                        }
                      }
                    }
                    uses export;
                  }
                  container unset {
                    augex:data-path "@unset";
                    presence "Config entry.";
                    uses var-action-list;
                  }
                  container export {
                    augex:data-path "@export";
                    presence "Config entry.";
                    uses var-action-list;
                  }
                  container builtin {
                    augex:data-path "@builtin";
                    augex:value-yang-path "shell-builtin-cmds";
                    presence "Config entry.";
                    leaf shell-builtin-cmds {
                      mandatory true;
                      type string {
                        pattern "(((ulimit)|(shift))|(exit))|(:)";
                      }
                    }
                    leaf args {
                      type string {
                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                      }
                      augex:data-path "args";
                    }
                  }
                  leaf return {
                    type union {
                      type empty;
                      type uint64;
                    }
                    augex:data-path "@return";
                  }
                  container condition {
                    augex:data-path "@condition";
                    augex:value-yang-path "sto-to-semicol";
                    presence "Config entry.";
                    uses type;
                  }
                  leaf eval {
                    type string {
                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                    }
                    augex:data-path "@eval";
                  }
                  container alias {
                    augex:data-path "@alias";
                    augex:value-yang-path "key";
                    presence "Config entry.";
                    leaf key {
                      mandatory true;
                      type string {
                        pattern "[-A-Za-z0-9_]+(\\[[0-9A-Za-z_,]+\\])?";
                        pattern "unset|export" {
                          modifier invert-match;
                        }
                      }
                    }
                    leaf value {
                      mandatory true;
                      type string {
                        pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                      }
                      augex:data-path "value";
                    }
                  }
                  list command-list {
                    key "_r-id";
                    leaf _r-id {
                      type uint64;
                      description
                        "Implicitly generated list key to maintain the recursive augeas data.";
                    }
                    container command {
                      augex:data-path "@command";
                      augex:value-yang-path "value";
                      presence "Config entry.";
                      uses key-list;
                      leaf value {
                        mandatory true;
                        type string {
                          pattern "$?[-A-Za-z0-9_./]+";
                          pattern "exit|shift|return|ulimit|unset|export|source|\\.|if|for|select|while|until|then|else|fi|done|case|eval|alias" {
                            modifier invert-match;
                          }
                        }
                      }
                      leaf arg {
                        type string {
                          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                        }
                        augex:data-path "@arg";
                      }
                      choice ch-command {
                        container pipe {
                          augex:data-path "@pipe";
                          presence "Config entry.";
                          list config-entries {
                            key "_id";
                            ordered-by user;
                            leaf _id {
                              type uint64;
                              description
                                "Implicitly generated list key to maintain the order of the augeas data.";
                            }
                            leaf _command-ref {
                              type leafref {
                                path "../../../../../command-list/_r-id";
                              }
                              description
                                "Implicitly generated leaf to maintain recursive augeas data.";
                            }
                          }
                        }
                        container and {
                          augex:data-path "@and";
                          presence "Config entry.";
                          list config-entries {
                            key "_id";
                            ordered-by user;
                            leaf _id {
                              type uint64;
                              description
                                "Implicitly generated list key to maintain the order of the augeas data.";
                            }
                            choice ch-config-entries {
                              mandatory true;
                              leaf source {
                                type string {
                                  pattern "[^;=# \t\n]+([^;=#\n]*[^;=# \t\n]+)*";
                                }
                                augex:data-path ".source";
                              }
                              container key {
                                augex:data-path "$$";
                                augex:value-yang-path "simple-value";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                uses export;
                              }
                              container unset {
                                augex:data-path "@unset";
                                presence "Config entry.";
                                uses var-action-list;
                              }
                              container export {
                                augex:data-path "@export";
                                presence "Config entry.";
                                uses var-action-list;
                              }
                              container builtin {
                                augex:data-path "@builtin";
                                augex:value-yang-path "shell-builtin-cmds";
                                presence "Config entry.";
                                leaf shell-builtin-cmds {
                                  mandatory true;
                                  type string {
                                    pattern "(((ulimit)|(shift))|(exit))|(:)";
                                  }
                                }
                                leaf args {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "args";
                                }
                              }
                              leaf return {
                                type union {
                                  type empty;
                                  type uint64;
                                }
                                augex:data-path "@return";
                              }
                              container condition {
                                augex:data-path "@condition";
                                augex:value-yang-path "sto-to-semicol";
                                presence "Config entry.";
                                uses type;
                              }
                              leaf eval {
                                type string {
                                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                }
                                augex:data-path "@eval";
                              }
                              container alias {
                                augex:data-path "@alias";
                                augex:value-yang-path "key";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                leaf value {
                                  mandatory true;
                                  type string {
                                    pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                  }
                                  augex:data-path "value";
                                }
                              }
                              leaf _command-ref {
                                type leafref {
                                  path "../../../../../command-list/_r-id";
                                }
                                description
                                  "Implicitly generated leaf to maintain recursive augeas data.";
                              }
                            }
                          }
                        }
                        container or {
                          augex:data-path "@or";
                          presence "Config entry.";
                          list config-entries {
                            key "_id";
                            ordered-by user;
                            leaf _id {
                              type uint64;
                              description
                                "Implicitly generated list key to maintain the order of the augeas data.";
                            }
                            choice ch-config-entries {
                              mandatory true;
                              leaf source {
                                type string {
                                  pattern "[^;=# \t\n]+([^;=#\n]*[^;=# \t\n]+)*";
                                }
                                augex:data-path ".source";
                              }
                              container key {
                                augex:data-path "$$";
                                augex:value-yang-path "simple-value";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                uses export;
                              }
                              container unset {
                                augex:data-path "@unset";
                                presence "Config entry.";
                                uses var-action-list;
                              }
                              container export {
                                augex:data-path "@export";
                                presence "Config entry.";
                                uses var-action-list;
                              }
                              container builtin {
                                augex:data-path "@builtin";
                                augex:value-yang-path "shell-builtin-cmds";
                                presence "Config entry.";
                                leaf shell-builtin-cmds {
                                  mandatory true;
                                  type string {
                                    pattern "(((ulimit)|(shift))|(exit))|(:)";
                                  }
                                }
                                leaf args {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "args";
                                }
                              }
                              leaf return {
                                type union {
                                  type empty;
                                  type uint64;
                                }
                                augex:data-path "@return";
                              }
                              container condition {
                                augex:data-path "@condition";
                                augex:value-yang-path "sto-to-semicol";
                                presence "Config entry.";
                                uses type;
                              }
                              leaf eval {
                                type string {
                                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                }
                                augex:data-path "@eval";
                              }
                              container alias {
                                augex:data-path "@alias";
                                augex:value-yang-path "key";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                leaf value {
                                  mandatory true;
                                  type string {
                                    pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                  }
                                  augex:data-path "value";
                                }
                              }
                              leaf _command-ref {
                                type leafref {
                                  path "../../../../../command-list/_r-id";
                                }
                                description
                                  "Implicitly generated leaf to maintain recursive augeas data.";
                              }
                            }
                          }
                        }
                      }
                    }
                  }
                  leaf _if-ref {
                    type leafref {
                      path "../../../../if-list/_r-id";
                    }
                    description
                      "Implicitly generated leaf to maintain recursive augeas data.";
                  }
                }
              }
            }
            container subshell {
              augex:data-path "@subshell";
              presence "Config entry.";
              list config-entries {
                key "_id";
                ordered-by user;
                leaf _id {
                  type uint64;
                  description
                    "Implicitly generated list key to maintain the order of the augeas data.";
                }
                choice ch-config-entries {
                  mandatory true;
                  leaf source {
                    type string {
                      pattern "[^;=# \t\n]+([^;=#\n]*[^;=# \t\n]+)*";
                    }
                    augex:data-path ".source";
                  }
                  container key {
                    augex:data-path "$$";
                    augex:value-yang-path "simple-value";
                    presence "Config entry.";
                    leaf key {
                      mandatory true;
                      type string {
                        pattern "[-A-Za-z0-9_]+(\\[[0-9A-Za-z_,]+\\])?";
                        pattern "unset|export" {
                          modifier invert-match;
                        }
                      }
                    }
                    uses export;
                  }
                  container unset {
                    augex:data-path "@unset";
                    presence "Config entry.";
                    uses var-action-list;
                  }
                  container export {
                    augex:data-path "@export";
                    presence "Config entry.";
                    uses var-action-list;
                  }
                  container builtin {
                    augex:data-path "@builtin";
                    augex:value-yang-path "shell-builtin-cmds";
                    presence "Config entry.";
                    leaf shell-builtin-cmds {
                      mandatory true;
                      type string {
                        pattern "(((ulimit)|(shift))|(exit))|(:)";
                      }
                    }
                    leaf args {
                      type string {
                        pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                      }
                      augex:data-path "args";
                    }
                  }
                  leaf return {
                    type union {
                      type empty;
                      type uint64;
                    }
                    augex:data-path "@return";
                  }
                  container condition {
                    augex:data-path "@condition";
                    augex:value-yang-path "sto-to-semicol";
                    presence "Config entry.";
                    uses type;
                  }
                  leaf eval {
                    type string {
                      pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                    }
                    augex:data-path "@eval";
                  }
                  container alias {
                    augex:data-path "@alias";
                    augex:value-yang-path "key";
                    presence "Config entry.";
                    leaf key {
                      mandatory true;
                      type string {
                        pattern "[-A-Za-z0-9_]+(\\[[0-9A-Za-z_,]+\\])?";
                        pattern "unset|export" {
                          modifier invert-match;
                        }
                      }
                    }
                    leaf value {
                      mandatory true;
                      type string {
                        pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                      }
                      augex:data-path "value";
                    }
                  }
                  list command-list {
                    key "_r-id";
                    leaf _r-id {
                      type uint64;
                      description
                        "Implicitly generated list key to maintain the recursive augeas data.";
                    }
                    container command {
                      augex:data-path "@command";
                      augex:value-yang-path "value";
                      presence "Config entry.";
                      uses key-list;
                      leaf value {
                        mandatory true;
                        type string {
                          pattern "$?[-A-Za-z0-9_./]+";
                          pattern "exit|shift|return|ulimit|unset|export|source|\\.|if|for|select|while|until|then|else|fi|done|case|eval|alias" {
                            modifier invert-match;
                          }
                        }
                      }
                      leaf arg {
                        type string {
                          pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                        }
                        augex:data-path "@arg";
                      }
                      choice ch-command {
                        container pipe {
                          augex:data-path "@pipe";
                          presence "Config entry.";
                          list config-entries {
                            key "_id";
                            ordered-by user;
                            leaf _id {
                              type uint64;
                              description
                                "Implicitly generated list key to maintain the order of the augeas data.";
                            }
                            leaf _command-ref {
                              type leafref {
                                path "../../../../../command-list/_r-id";
                              }
                              description
                                "Implicitly generated leaf to maintain recursive augeas data.";
                            }
                          }
                        }
                        container and {
                          augex:data-path "@and";
                          presence "Config entry.";
                          list config-entries {
                            key "_id";
                            ordered-by user;
                            leaf _id {
                              type uint64;
                              description
                                "Implicitly generated list key to maintain the order of the augeas data.";
                            }
                            choice ch-config-entries {
                              mandatory true;
                              leaf source {
                                type string {
                                  pattern "[^;=# \t\n]+([^;=#\n]*[^;=# \t\n]+)*";
                                }
                                augex:data-path ".source";
                              }
                              container key {
                                augex:data-path "$$";
                                augex:value-yang-path "simple-value";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                uses export;
                              }
                              container unset {
                                augex:data-path "@unset";
                                presence "Config entry.";
                                uses var-action-list;
                              }
                              container export {
                                augex:data-path "@export";
                                presence "Config entry.";
                                uses var-action-list;
                              }
                              container builtin {
                                augex:data-path "@builtin";
                                augex:value-yang-path "shell-builtin-cmds";
                                presence "Config entry.";
                                leaf shell-builtin-cmds {
                                  mandatory true;
                                  type string {
                                    pattern "(((ulimit)|(shift))|(exit))|(:)";
                                  }
                                }
                                leaf args {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "args";
                                }
                              }
                              leaf return {
                                type union {
                                  type empty;
                                  type uint64;
                                }
                                augex:data-path "@return";
                              }
                              container condition {
                                augex:data-path "@condition";
                                augex:value-yang-path "sto-to-semicol";
                                presence "Config entry.";
                                uses type;
                              }
                              leaf eval {
                                type string {
                                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                }
                                augex:data-path "@eval";
                              }
                              container alias {
                                augex:data-path "@alias";
                                augex:value-yang-path "key";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                leaf value {
                                  mandatory true;
                                  type string {
                                    pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                  }
                                  augex:data-path "value";
                                }
                              }
                              leaf _command-ref {
                                type leafref {
                                  path "../../../../../command-list/_r-id";
                                }
                                description
                                  "Implicitly generated leaf to maintain recursive augeas data.";
                              }
                            }
                          }
                        }
                        container or {
                          augex:data-path "@or";
                          presence "Config entry.";
                          list config-entries {
                            key "_id";
                            ordered-by user;
                            leaf _id {
                              type uint64;
                              description
                                "Implicitly generated list key to maintain the order of the augeas data.";
                            }
                            choice ch-config-entries {
                              mandatory true;
                              leaf source {
                                type string {
                                  pattern "[^;=# \t\n]+([^;=#\n]*[^;=# \t\n]+)*";
                                }
                                augex:data-path ".source";
                              }
                              container key {
                                augex:data-path "$$";
                                augex:value-yang-path "simple-value";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                uses export;
                              }
                              container unset {
                                augex:data-path "@unset";
                                presence "Config entry.";
                                uses var-action-list;
                              }
                              container export {
                                augex:data-path "@export";
                                presence "Config entry.";
                                uses var-action-list;
                              }
                              container builtin {
                                augex:data-path "@builtin";
                                augex:value-yang-path "shell-builtin-cmds";
                                presence "Config entry.";
                                leaf shell-builtin-cmds {
                                  mandatory true;
                                  type string {
                                    pattern "(((ulimit)|(shift))|(exit))|(:)";
                                  }
                                }
                                leaf args {
                                  type string {
                                    pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                  }
                                  augex:data-path "args";
                                }
                              }
                              leaf return {
                                type union {
                                  type empty;
                                  type uint64;
                                }
                                augex:data-path "@return";
                              }
                              container condition {
                                augex:data-path "@condition";
                                augex:value-yang-path "sto-to-semicol";
                                presence "Config entry.";
                                uses type;
                              }
                              leaf eval {
                                type string {
                                  pattern "(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``))(((([ \t]*\\\\\n[ \t]*)|([ \t]+))(((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)))*)";
                                }
                                augex:data-path "@eval";
                              }
                              container alias {
                                augex:data-path "@alias";
                                augex:value-yang-path "key";
                                presence "Config entry.";
                                leaf key {
                                  mandatory true;
                                  type string {
                                    pattern "[-A-Za-z0-9_]+(\\[[0-9A-Za-z_,]+\\])?";
                                    pattern "unset|export" {
                                      modifier invert-match;
                                    }
                                  }
                                }
                                leaf value {
                                  mandatory true;
                                  type string {
                                    pattern "((((((([^`;()'\"&|\n\\\\# \t]#*|\\\\.)|(((\")((([^\"\\\\]|\\\\.)|([ \t]*\\\\\n[ \t]*))*))(\")))|('[^']*'))|($\\([^\\\\(\\\\)#\n]*\\)))|($\\(\\([^\\\\)#\n]*\\)\\)))+)|(`[^`\n]+`))|(``[^` \t\n;]+``)";
                                  }
                                  augex:data-path "value";
                                }
                              }
                              leaf _command-ref {
                                type leafref {
                                  path "../../../../../command-list/_r-id";
                                }
                                description
                                  "Implicitly generated leaf to maintain recursive augeas data.";
                              }
                            }
                          }
                        }
                      }
                    }
                  }
                  leaf _if-ref {
                    type leafref {
                      path "../../../../if-list/_r-id";
                    }
                    description
                      "Implicitly generated leaf to maintain recursive augeas data.";
                  }
                }
              }
            }
          }
        }
      }
    }
  }
}
