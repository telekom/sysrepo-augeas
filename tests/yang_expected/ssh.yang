module ssh {
  yang-version 1.1;
  namespace "aug:ssh";
  prefix aug;

  import augeas-extension {
    prefix augex;
  }

  augex:augeas-mod-name "Ssh";

  grouping remote-fw {
    container node {
      augex:data-path "$$";
      augex:value-yang-path "value-to-eol";
      presence "Config entry.";
      leaf label {
        mandatory true;
        type string {
          pattern "[^ \t\n/=][^ \t\n/]*";
        }
      }
      leaf value-to-eol {
        mandatory true;
        type string {
          pattern "[^ \t\n].*[^ \t\n]|[^ \t\n]";
        }
      }
    }
  }
  grouping commas-entry-list {
    list commas-entry-list {
      key "_seq";
      min-elements 1;
      ordered-by user;
      augex:data-path "$$";
      augex:value-yang-path "value-to-comma";
      leaf _seq {
        type uint64;
        description
          "Key contains some unique value. The order is based on the actual order of list instances.";
      }
      leaf value-to-comma {
        mandatory true;
        type string {
          pattern "[^, \t\n=][^, \t\n]*";
        }
      }
    }
  }
  grouping match-entry {
    list match-entry {
      key "_id";
      ordered-by user;
      leaf _id {
        type uint64;
        description
          "Implicitly generated list key to maintain the order of the augeas data.";
      }
      choice ch-match-entry {
        mandatory true;
        container send-env {
          augex:data-path "$$";
          presence "Config entry.";
          leaf send-env {
            mandatory true;
            type string {
              pattern "(?i)SendEnv";
            }
          }
          list array-entry-list {
            key "_seq";
            ordered-by user;
            augex:data-path "$$";
            augex:value-yang-path "value-to-spc";
            leaf _seq {
              type uint64;
              description
                "Key contains some unique value. The order is based on the actual order of list instances.";
            }
            leaf value-to-spc {
              mandatory true;
              type string {
                pattern "[^ \t\n=][^ \t\n]*";
              }
            }
          }
        }
        container proxy-command {
          augex:data-path "$$";
          augex:value-yang-path "value-to-eol";
          presence "Config entry.";
          leaf proxy-command {
            mandatory true;
            type string {
              pattern "(?i)ProxyCommand";
            }
          }
          leaf value-to-eol {
            mandatory true;
            type string {
              pattern "[^ \t\n].*[^ \t\n]|[^ \t\n]";
            }
          }
        }
        container remote-fw {
          augex:data-path "$$";
          presence "Config entry.";
          leaf remote-forward {
            mandatory true;
            type string {
              pattern "(?i)RemoteForward";
            }
          }
          uses remote-fw;
        }
        container local-fw {
          augex:data-path "$$";
          presence "Config entry.";
          leaf local-forward {
            mandatory true;
            type string {
              pattern "(?i)LocalForward";
            }
          }
          uses remote-fw;
        }
        container macs {
          augex:data-path "$$";
          presence "Config entry.";
          leaf macs {
            mandatory true;
            type string {
              pattern "(?i)MACs";
            }
          }
          uses commas-entry-list;
        }
        container ciphers {
          augex:data-path "$$";
          presence "Config entry.";
          leaf ciphers {
            mandatory true;
            type string {
              pattern "(?i)Ciphers";
            }
          }
          uses commas-entry-list;
        }
        container host-key-algorithms {
          augex:data-path "$$";
          presence "Config entry.";
          leaf host-key-algorithms {
            mandatory true;
            type string {
              pattern "(?i)HostKeyAlgorithms";
            }
          }
          uses commas-entry-list;
        }
        container kex-algorithms {
          augex:data-path "$$";
          presence "Config entry.";
          leaf host-key-algorithms {
            mandatory true;
            type string {
              pattern "(?i)KexAlgorithms";
            }
          }
          uses commas-entry-list;
        }
        container pubkey-accepted-key-types {
          augex:data-path "$$";
          presence "Config entry.";
          leaf pubkey-accepted-key-types {
            mandatory true;
            type string {
              pattern "(?i)PubkeyAcceptedKeyTypes";
            }
          }
          uses commas-entry-list;
        }
        container global-knownhosts-file {
          augex:data-path "$$";
          presence "Config entry.";
          leaf global-known-hosts-file {
            mandatory true;
            type string {
              pattern "(?i)GlobalKnownHostsFile";
            }
          }
          list spaces-entry-list {
            key "_seq";
            min-elements 1;
            ordered-by user;
            augex:data-path "$$";
            augex:value-yang-path "value-to-spc";
            leaf _seq {
              type uint64;
              description
                "Key contains some unique value. The order is based on the actual order of list instances.";
            }
            leaf value-to-spc {
              mandatory true;
              type string {
                pattern "[^ \t\n=][^ \t\n]*";
              }
            }
          }
        }
        container rekey-limit {
          augex:data-path "$$";
          presence "Config entry.";
          leaf rekey-limit {
            mandatory true;
            type string {
              pattern "(?i)RekeyLimit";
            }
          }
          leaf amount {
            mandatory true;
            type string {
              pattern "[^ \t\n=][^ \t\n]*";
            }
            augex:data-path "amount";
          }
          leaf duration {
            type string {
              pattern "[^ \t\n=][^ \t\n]*";
            }
            augex:data-path "duration";
          }
        }
        container other-entry {
          augex:data-path "$$";
          augex:value-yang-path "value-to-spc";
          presence "Config entry.";
          leaf key {
            mandatory true;
            type string {
              pattern "[A-Za-z0-9]+";
              pattern "(?i)SendEnv|Host|Match|ProxyCommand|RemoteForward|LocalForward|MACs|Ciphers|(HostKey|Kex)Algorithms|PubkeyAcceptedKeyTypes|GlobalKnownHostsFile|RekeyLimit" {
                modifier invert-match;
              }
            }
          }
          leaf value-to-spc {
            mandatory true;
            type string {
              pattern "[^ \t\n=][^ \t\n]*";
            }
          }
        }
      }
    }
  }
  list ssh {
    key "config-file";
    leaf config-file {
      type string;
    }
    uses match-entry;
    list config-entries {
      key "_id";
      ordered-by user;
      leaf _id {
        type uint64;
        description
          "Implicitly generated list key to maintain the order of the augeas data.";
      }
      choice ch-config-entries {
        mandatory true;
        container host {
          augex:data-path "$$";
          augex:value-yang-path "value-to-eol";
          presence "Config entry.";
          leaf host {
            mandatory true;
            type string {
              pattern "(?i)Host";
            }
          }
          leaf value-to-eol {
            mandatory true;
            type string {
              pattern "[^ \t\n].*[^ \t\n]|[^ \t\n]";
            }
          }
          uses match-entry;
        }
        container match {
          augex:data-path "$$";
          presence "Config entry.";
          leaf match {
            mandatory true;
            type string {
              pattern "(?i)Match";
            }
          }
          container condition {
            augex:data-path "Condition";
            presence "Config entry.";
            list condition-entry-list {
              key "_id";
              min-elements 1;
              ordered-by user;
              leaf _id {
                type uint64;
                description
                  "Implicitly generated list key to maintain the order of the augeas data.";
              }
              container condition-entry {
                augex:data-path "$$";
                augex:value-yang-path "value";
                presence "Config entry.";
                leaf label {
                  mandatory true;
                  type string {
                    pattern "[A-Za-z0-9]+";
                  }
                }
                leaf value {
                  mandatory true;
                  type union {
                    type string {
                      pattern "[^\"' \t\n=]+";
                    }
                    type string {
                      pattern "[^\"'\t\n]* [^\"'\t\n]*";
                    }
                  }
                }
              }
            }
          }
          container settings {
            augex:data-path "Settings";
            presence "Config entry.";
            uses match-entry;
          }
        }
      }
    }
  }
}
