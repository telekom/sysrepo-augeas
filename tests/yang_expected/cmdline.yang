module cmdline {
  yang-version 1.1;
  namespace "aug:cmdline";
  prefix aug;

  import augeas-extension {
    prefix augex;
  }

  augex:augeas-mod-name "Cmdline";

  list cmdline {
    key "config-file";
    leaf config-file {
      type string;
    }
    list word-list {
      key "_id";
      ordered-by user;
      leaf _id {
        type uint64;
        description
          "Implicitly generated list key to maintain the order of the augeas data.";
      }
      container word {
        augex:data-path "$$";
        augex:value-yang-path "no-spaces";
        presence "Config entry.";
        leaf word {
          mandatory true;
          type string {
            pattern "[A-Za-z0-9_.-]+";
          }
        }
        leaf no-spaces {
          type string {
            pattern "[^ \t\n]+";
          }
        }
      }
    }
  }
}
