module postfix-passwordmap {
  yang-version 1.1;
  namespace "aug:postfix-passwordmap";
  prefix aug;

  import augeas-extension {
    prefix augex;
  }

  augex:augeas-mod-name "Postfix_Passwordmap";

  list postfix-passwordmap {
    key "config-file";
    leaf config-file {
      type string;
    }
    list record-list {
      key "_id";
      ordered-by user;
      leaf _id {
        type uint64;
        description
          "Implicitly generated list key to maintain the order of the augeas data.";
      }
      container pattern {
        augex:data-path "pattern";
        augex:value-yang-path "value";
        presence "Config entry.";
        leaf value {
          mandatory true;
          type string {
            pattern "\\[?[A-Za-z0-9@\\\\*.-]+\\]?(:?[A-Za-z0-9]*)*";
          }
        }
        leaf username {
          mandatory true;
          type string {
            pattern "[A-Za-z0-9@_\\\\+\\\\*.-]+";
          }
          augex:data-path "username";
        }
        leaf password {
          mandatory true;
          type union {
            type empty;
            type string {
              pattern "[^ \t\n].*[^ \t\n]|[^ \t\n]";
            }
          }
          augex:data-path "password";
        }
      }
    }
  }
}
