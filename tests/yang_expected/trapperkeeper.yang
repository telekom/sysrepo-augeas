module trapperkeeper {
  yang-version 1.1;
  namespace "aug:trapperkeeper";
  prefix aug;

  import augeas-extension {
    prefix augex;
  }

  augex:augeas-mod-name "Trapperkeeper";

  list trapperkeeper {
    key "config-file";
    leaf config-file {
      type string;
    }
    list entry-list {
      key "_id";
      ordered-by user;
      leaf _id {
        type uint64;
        description
          "Implicitly generated list key to maintain the order of the augeas data.";
      }
      list hash-list {
        key "_r-id";
        leaf _r-id {
          type uint64;
          description
            "Implicitly generated list key to maintain the recursive augeas data.";
        }
        container hash {
          augex:data-path "@hash";
          augex:value-yang-path "word";
          presence "Config entry.";
          leaf word {
            mandatory true;
            type string {
              pattern "[A-Za-z0-9_.-]+";
            }
          }
          list config-entries {
            key "_id";
            ordered-by user;
            leaf _id {
              type uint64;
              description
                "Implicitly generated list key to maintain the order of the augeas data.";
            }
            choice ch-config-entries {
              mandatory true;
              leaf _hash-ref {
                type leafref {
                  path "../../../../hash-list/_r-id";
                }
                description
                  "Implicitly generated leaf to maintain recursive augeas data.";
              }
              container simple {
                augex:data-path "@simple";
                augex:value-yang-path "value";
                presence "Config entry.";
                leaf value {
                  mandatory true;
                  type string {
                    pattern "[A-Za-z0-9_./-]+";
                  }
                }
                leaf value2 {
                  mandatory true;
                  type string {
                    pattern "[^,\"\\\\\\[ \t\n]+";
                  }
                  augex:data-path "@value";
                }
              }
              container array {
                augex:data-path "@array";
                augex:value-yang-path "word";
                presence "Config entry.";
                leaf word {
                  mandatory true;
                  type string {
                    pattern "[A-Za-z0-9_.-]+";
                  }
                }
                list elem-list {
                  key "_seq";
                  ordered-by user;
                  augex:data-path "$$";
                  augex:value-yang-path "value";
                  leaf _seq {
                    type uint64;
                    description
                      "Key contains some unique value. The order is based on the actual order of list instances.";
                  }
                  leaf value {
                    mandatory true;
                    type string {
                      pattern "[^,\"\\\\\\[ \t\n]+";
                    }
                  }
                }
              }
            }
          }
        }
      }
    }
  }
}
