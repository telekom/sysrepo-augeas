module ethers {
  yang-version 1.1;
  namespace "aug:ethers";
  prefix aug;

  import augeas-extension {
    prefix augex;
  }

  augex:augeas-mod-name "Ethers";

  list ethers {
    key "config-file";
    leaf config-file {
      type string;
    }
    list ether-list {
      key "_seq";
      ordered-by user;
      augex:data-path "$$";
      leaf _seq {
        type uint64;
        description
          "Key contains some unique value. The order is based on the actual order of list instances.";
      }
      leaf mac {
        mandatory true;
        type string {
          pattern "(((((((((([0-9a-fA-F][0-9a-fA-F]?)(:))([0-9a-fA-F][0-9a-fA-F]?))(:))([0-9a-fA-F][0-9a-fA-F]?))(:))([0-9a-fA-F][0-9a-fA-F]?))(:))([0-9a-fA-F][0-9a-fA-F]?))(:))([0-9a-fA-F][0-9a-fA-F]?)";
        }
        augex:data-path "mac";
      }
      leaf ip {
        mandatory true;
        type string {
          pattern "[^# \n\t]+";
        }
        augex:data-path "ip";
      }
    }
  }
}
