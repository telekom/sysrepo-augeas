module host-conf {
  yang-version 1.1;
  namespace "aug:host-conf";
  prefix aug;

  import augeas-extension {
    prefix augex;
  }

  augex:augeas-mod-name "Host_Conf";

  list host-conf {
    key "config-file";
    leaf config-file {
      type string;
    }
    list config-entries {
      key "_id";
      ordered-by user;
      leaf _id {
        type uint64;
        description
          "Implicitly generated list key to maintain the order of the augeas data.";
      }
      choice ch-config-entries {
        mandatory true;
        leaf multi {
          type string {
            pattern "(on)|(off)";
          }
          augex:data-path "multi";
        }
        leaf nospoof {
          type string {
            pattern "(on)|(off)";
          }
          augex:data-path "nospoof";
        }
        leaf spoofalert {
          type string {
            pattern "(on)|(off)";
          }
          augex:data-path "spoofalert";
        }
        leaf reorder {
          type string {
            pattern "(on)|(off)";
          }
          augex:data-path "reorder";
        }
        leaf spoof {
          type string {
            pattern "(((on)|(off))|(warn))|(nowarn)";
          }
          augex:data-path "spoof";
        }
        container order {
          augex:data-path "order";
          presence "Config entry.";
          list order-list {
            key "_seq";
            min-elements 1;
            ordered-by user;
            augex:data-path "$$";
            augex:value-yang-path "word";
            leaf _seq {
              type uint64;
              description
                "Key contains some unique value. The order is based on the actual order of list instances.";
            }
            leaf word {
              mandatory true;
              type string {
                pattern "[A-Za-z0-9_.-]+";
              }
            }
          }
        }
        container trim {
          augex:data-path "trim";
          presence "Config entry.";
          list trim-list {
            key "_seq";
            min-elements 1;
            ordered-by user;
            augex:data-path "$$";
            augex:value-yang-path "word";
            leaf _seq {
              type uint64;
              description
                "Key contains some unique value. The order is based on the actual order of list instances.";
            }
            leaf word {
              mandatory true;
              type string {
                pattern "[A-Za-z0-9_.-]+";
              }
            }
          }
        }
      }
    }
  }
}
