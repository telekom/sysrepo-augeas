module inetd {
  yang-version 1.1;
  namespace "aug:inetd";
  prefix aug;

  import augeas-extension {
    prefix augex;
  }

  augex:augeas-mod-name "Inetd";

  grouping address {
    list addrseq-list {
      key "_seq";
      min-elements 1;
      ordered-by user;
      augex:data-path "$$";
      augex:value-yang-path "value";
      leaf _seq {
        type uint64;
        description
          "Key contains some unique value. The order is based on the actual order of list instances.";
      }
      leaf value {
        mandatory true;
        type string {
          pattern "[a-zA-Z0-9.-]+|\\[[A-Za-z0-9:?*%]+\\]|\\*";
        }
      }
    }
  }
  grouping argument {
    list argseq-list {
      key "_seq";
      min-elements 1;
      ordered-by user;
      augex:data-path "$$";
      augex:value-yang-path "value";
      leaf _seq {
        type uint64;
        description
          "Key contains some unique value. The order is based on the actual order of list instances.";
      }
      leaf value {
        mandatory true;
        type string {
          pattern "[^ \t\n]+";
        }
      }
    }
  }
  list inetd {
    key "config-file";
    leaf config-file {
      type string;
    }
    list config-entries {
      key "_id";
      ordered-by user;
      leaf _id {
        type uint64;
        description
          "Implicitly generated list key to maintain the order of the augeas data.";
      }
      choice ch-config-entries {
        mandatory true;
        container service {
          augex:data-path "service";
          augex:value-yang-path "value";
          presence "Config entry.";
          container address {
            augex:data-path "address";
            presence "Config entry.";
            uses address;
          }
          leaf value {
            mandatory true;
            type string {
              pattern "[^ \t\n/:#]+";
            }
          }
          leaf socket {
            mandatory true;
            type string {
              pattern "[^ \t\n#]+";
            }
            augex:data-path "socket";
          }
          leaf protocol {
            mandatory true;
            type string {
              pattern "[^ \t\n,#]+";
            }
            augex:data-path "protocol";
          }
          leaf sndbuf {
            type string {
              pattern "[^ \t\n,]+";
            }
            augex:data-path "sndbuf";
          }
          leaf rcvbuf {
            type string {
              pattern "[^ \t\n,]+";
            }
            augex:data-path "rcvbuf";
          }
          leaf wait {
            mandatory true;
            type string {
              pattern "wait|nowait";
            }
            augex:data-path "wait";
          }
          leaf max {
            type uint64;
            augex:data-path "max";
          }
          leaf user {
            mandatory true;
            type string {
              pattern "[^ \t\n:.]+";
            }
            augex:data-path "user";
          }
          leaf group {
            type string {
              pattern "[^ \t\n:.]+";
            }
            augex:data-path "group";
          }
          leaf command {
            mandatory true;
            type string {
              pattern "[^ \t\n]+";
            }
            augex:data-path "command";
          }
          container arguments {
            augex:data-path "arguments";
            presence "Config entry.";
            uses argument;
          }
        }
        container rpc-service {
          augex:data-path "rpc_service";
          augex:value-yang-path "value";
          presence "Config entry.";
          container address {
            augex:data-path "address";
            presence "Config entry.";
            uses address;
          }
          leaf value {
            mandatory true;
            type string {
              pattern "[^ \t\n/:#]+";
            }
          }
          leaf version {
            mandatory true;
            type uint64;
            augex:data-path "version";
          }
          leaf endpoint-type {
            mandatory true;
            type string {
              pattern "[A-Za-z0-9_.-]+";
            }
            augex:data-path "endpoint-type";
          }
          list protocol-list {
            key "_id";
            min-elements 1;
            ordered-by user;
            leaf _id {
              type uint64;
              description
                "Implicitly generated list key to maintain the order of the augeas data.";
            }
            leaf protocol {
              mandatory true;
              type string {
                pattern "[^ \t\n,#]+";
              }
              augex:data-path "protocol";
            }
          }
          leaf wait {
            mandatory true;
            type string {
              pattern "wait|nowait";
            }
            augex:data-path "wait";
          }
          leaf max {
            type uint64;
            augex:data-path "max";
          }
          leaf user {
            mandatory true;
            type string {
              pattern "[^ \t\n:.]+";
            }
            augex:data-path "user";
          }
          leaf group {
            type string {
              pattern "[^ \t\n:.]+";
            }
            augex:data-path "group";
          }
          leaf command {
            mandatory true;
            type string {
              pattern "[^ \t\n]+";
            }
            augex:data-path "command";
          }
          container arguments {
            augex:data-path "arguments";
            presence "Config entry.";
            uses argument;
          }
        }
        container address {
          augex:data-path "address";
          presence "Config entry.";
          uses address;
        }
      }
    }
  }
}
