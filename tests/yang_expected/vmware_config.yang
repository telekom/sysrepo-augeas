module vmware_config {
  namespace "aug:vmware_config";
  prefix aug;

  import augeas-extension {
    prefix augex;
  }

  augex:augeas-mod-name "VMware_Config";

  list vmware_config {
    key "config-file";
    leaf config-file {
      type string;
    }
    list entry-list {
      key "_id";
      ordered-by user;
      leaf _id {
        type uint64;
        description
          "Implicitly generated list key to maintain the order of the augeas data.";
      }
      container entry {
        augex:data-path "$$";
        augex:value-yang-path "value";
        presence "Config entry.";
        leaf word {
          mandatory true;
          type string {
            pattern "[A-Za-z0-9_.-]+";
          }
        }
        leaf value {
          mandatory true;
          type string {
            pattern "[^\n\t \"]([^\n\"]*[^\n\t \"])?";
          }
        }
      }
    }
  }
}
