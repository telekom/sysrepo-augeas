module access {
  yang-version 1.1;
  namespace "aug:access";
  prefix aug;

  import augeas-extension {
    prefix augex;
  }

  augex:augeas-mod-name "Access";

  grouping entry {
    list config-entries {
      key "_id";
      min-elements 1;
      ordered-by user;
      leaf _id {
        type uint64;
        description
          "Implicitly generated list key to maintain the order of the augeas data.";
      }
      choice ch-config-entries {
        mandatory true;
        container user {
          augex:data-path "user";
          augex:value-yang-path "value";
          presence "Config entry.";
          leaf value {
            mandatory true;
            type union {
              type string {
                pattern "[Ee][Xx][Cc][Ee][Pp](([Tt][.0-9A-Z\\\\_a-z-]|[.0-9A-SU-Z\\\\_a-su-z-])[.0-9A-Z\\\\_a-z-]*|())|[Ee][Xx][Cc][Ee]([.0-9A-OQ-Z\\\\_a-oq-z-][.0-9A-Z\\\\_a-z-]*|())|[Ee][Xx][Cc]([.0-9A-DF-Z\\\\_a-df-z-][.0-9A-Z\\\\_a-z-]*|())|[Ee][Xx]([.0-9ABD-Z\\\\_abd-z-][.0-9A-Z\\\\_a-z-]*|())|([Ee][.0-9A-WYZ\\\\_a-wyz-]|[.0-9A-DF-Z\\\\_a-df-z-][.0-9A-Z\\\\_a-z-])[.0-9A-Z\\\\_a-z-]*|[Ee]|[.0-9A-DF-Z\\\\_a-df-z-]";
              }
              type string {
                pattern "[A-Za-z0-9_.-]+";
              }
            }
          }
          leaf host {
            type string {
              pattern "[A-Za-z0-9_.-]+";
            }
            augex:data-path "host";
            when "re-match(../value, '[A-Za-z0-9_.-]+')";
          }
        }
        leaf group {
          type string {
            pattern "[A-Za-z0-9_.\\\\-]+";
          }
          augex:data-path "group";
        }
        container netgroup {
          augex:data-path "netgroup";
          augex:value-yang-path "user";
          presence "Config entry.";
          leaf user {
            mandatory true;
            type string {
              pattern "[A-Za-z0-9_.\\\\-]+";
              pattern "[Ee][Xx][Cc][Ee][Pp][Tt]" {
                modifier invert-match;
              }
            }
          }
          leaf nisdomain {
            type string {
              pattern "[A-Za-z0-9_.-]+";
            }
            augex:data-path "nisdomain";
          }
        }
      }
    }
  }
  grouping origin-list {
    list origin-list {
      key "_id";
      min-elements 1;
      ordered-by user;
      leaf _id {
        type uint64;
        description
          "Implicitly generated list key to maintain the order of the augeas data.";
      }
      leaf origin {
        mandatory true;
        type string {
          pattern "[^ \t\n]+";
          pattern "[Ee][Xx][Cc][Ee][Pp][Tt]" {
            modifier invert-match;
          }
        }
        augex:data-path "origin";
      }
    }
  }
  list access {
    key "config-file";
    leaf config-file {
      type string;
    }
    list entry-list {
      key "_id";
      ordered-by user;
      leaf _id {
        type uint64;
        description
          "Implicitly generated list key to maintain the order of the augeas data.";
      }
      container access {
        augex:data-path "access";
        augex:value-yang-path "value";
        presence "Config entry.";
        leaf value {
          mandatory true;
          type string {
            pattern "[+-]";
          }
        }
        uses entry;
        container except {
          augex:data-path "except";
          presence "Config entry.";
          uses entry;
        }
        uses origin-list;
        container except2 {
          augex:data-path "except";
          presence "Config entry.";
          uses origin-list;
        }
      }
    }
  }
}
