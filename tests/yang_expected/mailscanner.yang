module mailscanner {
  yang-version 1.1;
  namespace "aug:mailscanner";
  prefix aug;

  import augeas-extension {
    prefix augex;
  }

  augex:augeas-mod-name "Mailscanner";

  list mailscanner {
    key "config-file";
    leaf config-file {
      type string;
    }
    list config-entries {
      key "_id";
      ordered-by user;
      leaf _id {
        type uint64;
        description
          "Implicitly generated list key to maintain the order of the augeas data.";
      }
      choice ch-config-entries {
        mandatory true;
        leaf include {
          type string {
            pattern "[^ =\t\n]+";
          }
          augex:data-path "include";
        }
        container normal-line {
          augex:data-path "$$";
          augex:value-yang-path "line-value";
          presence "Config entry.";
          leaf keys {
            mandatory true;
            type string {
              pattern "[A-Za-z%][ :<>%A-Za-z0-9_.-]+[A-Za-z%2]";
              pattern "include" {
                modifier invert-match;
              }
            }
          }
          leaf line-value {
            type string {
              pattern "((([^# \t\n])(.*))([^# \t\n]))|([^# \t\n])";
            }
          }
        }
      }
    }
  }
}
