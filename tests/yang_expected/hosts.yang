module hosts {
  yang-version 1.1;
  namespace "aug:hosts";
  prefix aug;

  import augeas-extension {
    prefix augex;
  }

  augex:augeas-mod-name "Hosts";

  list hosts {
    key "config-file";
    leaf config-file {
      type string;
    }
    list host-list {
      key "_seq";
      ordered-by user;
      augex:data-path "$$";
      leaf _seq {
        type uint64;
        description
          "Key contains some unique value. The order is based on the actual order of list instances.";
      }
      leaf ipaddr {
        mandatory true;
        type string {
          pattern "[^# \n\t]+";
        }
        augex:data-path "ipaddr";
      }
      leaf canonical {
        mandatory true;
        type string {
          pattern "[^# \n\t]+";
        }
        augex:data-path "canonical";
      }
      list alias-list {
        key "_id";
        ordered-by user;
        leaf _id {
          type uint64;
          description
            "Implicitly generated list key to maintain the order of the augeas data.";
        }
        leaf alias {
          mandatory true;
          type string {
            pattern "[^# \n\t]+";
          }
          augex:data-path "alias";
        }
      }
    }
  }
}
