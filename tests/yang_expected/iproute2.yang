module iproute2 {
  yang-version 1.1;
  namespace "aug:iproute2";
  prefix aug;

  import augeas-extension {
    prefix augex;
  }

  augex:augeas-mod-name "IPRoute2";

  list iproute2 {
    key "config-file";
    leaf config-file {
      type string;
    }
    list record-list {
      key "_id";
      ordered-by user;
      leaf _id {
        type uint64;
        description
          "Implicitly generated list key to maintain the order of the augeas data.";
      }
      container record {
        augex:data-path "$$";
        augex:value-yang-path "value";
        presence "Config entry.";
        leaf id {
          mandatory true;
          type string {
            pattern "(0x[0-9a-fA-F]+)|([0-9]+)";
          }
        }
        leaf value {
          mandatory true;
          type string {
            pattern "[a-zA-Z0-9/-]+";
          }
        }
      }
    }
  }
}
