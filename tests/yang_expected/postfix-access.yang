module postfix-access {
  yang-version 1.1;
  namespace "aug:postfix-access";
  prefix aug;

  import augeas-extension {
    prefix augex;
  }

  augex:augeas-mod-name "Postfix_Access";

  list postfix-access {
    key "config-file";
    leaf config-file {
      type string;
    }
    list spec-list {
      key "_seq";
      ordered-by user;
      augex:data-path "$$";
      leaf _seq {
        type uint64;
        description
          "Key contains some unique value. The order is based on the actual order of list instances.";
      }
      leaf pattern {
        mandatory true;
        type string {
          pattern "([^# \n\t])+";
        }
        augex:data-path "pattern";
      }
      leaf action {
        mandatory true;
        type string {
          pattern "([^# \n\t])+";
        }
        augex:data-path "action";
      }
      leaf parameters {
        type string {
          pattern "([^# \n\t])|((([^# \n\t])((([^#\n])|(\n[ \t]+))*))([^# \n\t]))";
        }
        augex:data-path "parameters";
      }
    }
  }
}
