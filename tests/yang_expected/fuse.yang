module fuse {
  yang-version 1.1;
  namespace "aug:fuse";
  prefix aug;

  import augeas-extension {
    prefix augex;
  }

  augex:augeas-mod-name "Fuse";

  list fuse {
    key "config-file";
    leaf config-file {
      type string;
    }
    list config-entries {
      key "_id";
      ordered-by user;
      leaf _id {
        type uint64;
        description
          "Implicitly generated list key to maintain the order of the augeas data.";
      }
      choice ch-config-entries {
        mandatory true;
        leaf mount-max {
          type uint64;
          augex:data-path "mount_max";
        }
        leaf user-allow-other {
          type empty;
          augex:data-path "user_allow_other";
        }
      }
    }
  }
}
