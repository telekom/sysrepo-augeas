module ldif {
  yang-version 1.1;
  namespace "aug:ldif";
  prefix aug;

  import augeas-extension {
    prefix augex;
  }

  augex:augeas-mod-name "Ldif";

  grouping include {
    leaf include {
      mandatory true;
      type string {
        pattern "[^ \t\n][^\n]*";
      }
      augex:data-path "include";
    }
  }
  grouping option-list {
    list option-list {
      key "_id";
      ordered-by user;
      leaf _id {
        type uint64;
        description
          "Implicitly generated list key to maintain the order of the augeas data.";
      }
      leaf option {
        mandatory true;
        type string {
          pattern "[a-zA-Z0-9-]+";
        }
        augex:data-path "@option";
      }
    }
  }
  grouping attr-val-spec {
    container attr-val-spec {
      augex:data-path "$$";
      augex:value-yang-path "value";
      presence "Config entry.";
      leaf attr-type {
        mandatory true;
        type string {
          pattern "([0-9][0-9\\\\.]*)|([Cc][Hh][Aa][Nn][Gg][Ee][Tt][0-9A-XZa-xz-][0-9A-Za-z-][0-9A-Za-z-]*|[Cc][Hh][Aa][Nn][Gg][Ee][Tt][0-9A-XZa-xz-]|[Cc][Hh][Aa][Nn][Gg][Ee][Tt]|[Cc][Hh][Aa][Nn][Gg][0-9A-DF-Za-df-z-][0-9A-Za-z-][0-9A-Za-z-]*|[Cc][Hh][Aa][Nn][Gg][0-9A-DF-Za-df-z-]|[Cc][Hh][Aa][Nn][Gg]|[Cc][Hh][Aa][Nn][0-9A-FH-Za-fh-z-][0-9A-Za-z-][0-9A-Za-z-]*|[Cc][Hh][Aa][Nn][0-9A-FH-Za-fh-z-]|[Cc][Hh][Aa][Nn]|[Cc][Hh][Aa][0-9A-MO-Za-mo-z-][0-9A-Za-z-][0-9A-Za-z-]*|[Cc][Hh][Aa][0-9A-MO-Za-mo-z-]|[Cc][Hh][Aa]|[Cc][Hh][0-9B-Zb-z-][0-9A-Za-z-][0-9A-Za-z-]*|[Cc][Hh][0-9B-Zb-z-]|[Cc][Hh]|[Cc][0-9A-GI-Za-gi-z-]([0-9A-Za-z-][0-9A-Za-z-][0-9A-Za-z-]*|[0-9A-Za-z-]|())|[Cc][Hh][Aa][Nn][Gg][Ee][Tt][Yy][0-9A-OQ-Za-oq-z-][0-9A-Za-z-][0-9A-Za-z-]*|[Cc][Hh][Aa][Nn][Gg][Ee][Tt][Yy][0-9A-OQ-Za-oq-z-]|[Cc][Hh][Aa][Nn][Gg][Ee][Tt][Yy]|([Cc][Hh][Aa][Nn][Gg][Ee][Tt][Yy][Pp][Ee][0-9A-Za-z-][0-9A-Za-z-]|[Cc][Hh][Aa][Nn][Gg][Ee][Tt][Yy][Pp][0-9A-DF-Za-df-z-][0-9A-Za-z-])[0-9A-Za-z-]*|[Cc][Hh][Aa][Nn][Gg][Ee][Tt][Yy][Pp][Ee][0-9A-Za-z-]|[Cc][Hh][Aa][Nn][Gg][Ee][Tt][Yy][Pp][0-9A-DF-Za-df-z-]|[Cc][Hh][Aa][Nn][Gg][Ee][Tt][Yy][Pp]|[Cc][Hh][Aa][Nn][Gg][Ee][0-9A-SU-Za-su-z-][0-9A-Za-z-][0-9A-Za-z-]*|[Cc][Hh][Aa][Nn][Gg][Ee][0-9A-SU-Za-su-z-]|[Cc][Hh][Aa][Nn][Gg][Ee]|[Dd][Nn][0-9A-Za-z-][0-9A-Za-z-]([0-9A-Za-z-][0-9A-Za-z-]*|())|[Dd][0-9A-MO-Za-mo-z-][0-9A-Za-z-][0-9A-Za-z-][0-9A-Za-z-]*|[Dd][0-9A-MO-Za-mo-z-][0-9A-Za-z-]|[Ii][Nn][Cc][Ll][Uu][Dd](([Ee][0-9A-Za-z-]|[0-9A-DF-Za-df-z-])[0-9A-Za-z-]*|())|[Ii][Nn][Cc][Ll][Uu]([0-9A-CE-Za-ce-z-][0-9A-Za-z-]*|())|[Ii][Nn][Cc][Ll]([0-9A-TV-Za-tv-z-][0-9A-Za-z-]*|())|([Ii][Nn][Cc][0-9A-KM-Za-km-z-]|([Ii][Nn][0-9ABD-Zabd-z-]|([Ii][0-9A-MO-Za-mo-z-]|[ABE-HJ-Zabe-hj-z][0-9A-Za-z-])[0-9A-Za-z-])[0-9A-Za-z-])[0-9A-Za-z-]*|[Ii][Nn][Cc]|[Ii][Nn][0-9ABD-Zabd-z-]|([Ii][0-9A-MO-Za-mo-z-]|[ABE-HJ-Zabe-hj-z][0-9A-Za-z-])[0-9A-Za-z-]|[Ii][Nn]|[Ii][0-9A-MO-Za-mo-z-]|[ABE-HJ-Zabe-hj-z][0-9A-Za-z-]|[Ii]|[ABE-HJ-Zabe-hj-z]|[Dd]|[Dd][Nn][0-9A-Za-z-]|[Dd][0-9A-MO-Za-mo-z-]|[Cc])";
        }
      }
      uses option-list;
      choice ch-attr-val-spec {
        mandatory true;
        leaf value {
          type string {
            pattern "([^ \t\n:<][^\n]*)((\n[ \t]+[^ \t\n][^\n]*)*)";
          }
        }
        leaf base64 {
          type string {
            pattern "([a-zA-Z0-9=+]+)(((\n[ \t]+)([a-zA-Z0-9=+]+))*)";
          }
          augex:data-path "@base64";
        }
        leaf url {
          type string {
            pattern "([^ \t\n][^\n]*)(((\n[ \t]+)([^ \t\n][^\n]*))*)";
          }
          augex:data-path "@url";
        }
      }
    }
  }
  grouping option-list2 {
    uses option-list;
    list attr-val-spec-list {
      key "_id";
      ordered-by user;
      leaf _id {
        type uint64;
        description
          "Implicitly generated list key to maintain the order of the augeas data.";
      }
      uses attr-val-spec;
    }
  }
  list ldif {
    key "config-file";
    leaf config-file {
      type string;
    }
    choice ch-ldif {
      mandatory true;
      list sep-record {
        key "_id";
        ordered-by user;
        leaf _id {
          type uint64;
          description
            "Implicitly generated list key to maintain the order of the augeas data.";
        }
        uses include;
      }
      container content {
        augex:data-path "@content";
        presence "Config entry.";
        list sep-record {
          key "_id";
          ordered-by user;
          leaf _id {
            type uint64;
            description
              "Implicitly generated list key to maintain the order of the augeas data.";
          }
          uses include;
        }
        leaf version {
          type uint64;
          augex:data-path "version";
        }
        list sep-record2 {
          key "_id";
          ordered-by user;
          leaf _id {
            type uint64;
            description
              "Implicitly generated list key to maintain the order of the augeas data.";
          }
          uses include;
        }
        list record-list {
          key "_seq";
          min-elements 1;
          ordered-by user;
          augex:data-path "$$";
          augex:value-yang-path "value";
          leaf _seq {
            type uint64;
            description
              "Key contains some unique value. The order is based on the actual order of list instances.";
          }
          choice ch-record-list {
            mandatory true;
            leaf value {
              type string {
                pattern "([^ \t\n:<][^\n]*)((\n[ \t]+[^ \t\n][^\n]*)*)";
              }
            }
            leaf base64 {
              type string {
                pattern "([a-zA-Z0-9=+]+)(((\n[ \t]+)([a-zA-Z0-9=+]+))*)";
              }
              augex:data-path "@base64";
            }
          }
          list attr-val-spec-list {
            key "_id";
            min-elements 1;
            ordered-by user;
            leaf _id {
              type uint64;
              description
                "Implicitly generated list key to maintain the order of the augeas data.";
            }
            uses attr-val-spec;
          }
        }
        list sep-record3 {
          key "_id";
          ordered-by user;
          leaf _id {
            type uint64;
            description
              "Implicitly generated list key to maintain the order of the augeas data.";
          }
          uses include;
        }
      }
      container changes {
        augex:data-path "@changes";
        presence "Config entry.";
        list sep-record {
          key "_id";
          ordered-by user;
          leaf _id {
            type uint64;
            description
              "Implicitly generated list key to maintain the order of the augeas data.";
          }
          uses include;
        }
        leaf version {
          type uint64;
          augex:data-path "version";
        }
        list sep-record2 {
          key "_id";
          ordered-by user;
          leaf _id {
            type uint64;
            description
              "Implicitly generated list key to maintain the order of the augeas data.";
          }
          uses include;
        }
        list record-list {
          key "_seq";
          min-elements 1;
          ordered-by user;
          augex:data-path "$$";
          augex:value-yang-path "value";
          leaf _seq {
            type uint64;
            description
              "Key contains some unique value. The order is based on the actual order of list instances.";
          }
          choice ch-record-list {
            mandatory true;
            leaf value {
              type string {
                pattern "([^ \t\n:<][^\n]*)((\n[ \t]+[^ \t\n][^\n]*)*)";
              }
            }
            leaf base64 {
              type string {
                pattern "([a-zA-Z0-9=+]+)(((\n[ \t]+)([a-zA-Z0-9=+]+))*)";
              }
              augex:data-path "@base64";
            }
          }
          list change-control-list {
            key "_id";
            ordered-by user;
            leaf _id {
              type uint64;
              description
                "Implicitly generated list key to maintain the order of the augeas data.";
            }
            container control {
              augex:data-path "control";
              augex:value-yang-path "ldapoid";
              presence "Config entry.";
              leaf ldapoid {
                mandatory true;
                type string {
                  pattern "[0-9][0-9\\\\.]*";
                }
              }
              leaf criticality {
                type boolean;
                augex:data-path "criticality";
              }
              container value {
                augex:data-path "value";
                augex:value-yang-path "value";
                presence "Config entry.";
                choice ch-value {
                  mandatory true;
                  leaf value {
                    type string {
                      pattern "([^ \t\n:<][^\n]*)((\n[ \t]+[^ \t\n][^\n]*)*)";
                    }
                  }
                  leaf base64 {
                    type string {
                      pattern "([a-zA-Z0-9=+]+)(((\n[ \t]+)([a-zA-Z0-9=+]+))*)";
                    }
                    augex:data-path "@base64";
                  }
                  leaf url {
                    type string {
                      pattern "([^ \t\n][^\n]*)(((\n[ \t]+)([^ \t\n][^\n]*))*)";
                    }
                    augex:data-path "@url";
                  }
                }
              }
            }
          }
          container change-type {
            augex:data-path "$$";
            augex:value-yang-path "value";
            presence "Config entry.";
            leaf change-type {
              mandatory true;
              type string {
                pattern "(?i)changeType";
              }
            }
            leaf value {
              mandatory true;
              type union {
                type string {
                  pattern "add";
                }
                type string {
                  pattern "delete";
                }
                type string {
                  pattern "modify";
                }
                type string {
                  pattern "modr?dn";
                }
              }
            }
          }
          choice ch-record-list2 {
            list attr-val-spec-list {
              key "_id";
              when "../change-type/value='add'";
              ordered-by user;
              leaf _id {
                type uint64;
                description
                  "Implicitly generated list key to maintain the order of the augeas data.";
              }
              uses attr-val-spec;
            }
            list change-modify {
              key "_id";
              when "../change-type/value='modify'";
              ordered-by user;
              leaf _id {
                type uint64;
                description
                  "Implicitly generated list key to maintain the order of the augeas data.";
              }
              choice ch-change-modify {
                mandatory true;
                container add {
                  augex:data-path "add";
                  augex:value-yang-path "attr-type";
                  presence "Config entry.";
                  leaf attr-type {
                    mandatory true;
                    type string {
                      pattern "([0-9][0-9\\\\.]*)|([Cc][Hh][Aa][Nn][Gg][Ee][Tt][0-9A-XZa-xz-][0-9A-Za-z-][0-9A-Za-z-]*|[Cc][Hh][Aa][Nn][Gg][Ee][Tt][0-9A-XZa-xz-]|[Cc][Hh][Aa][Nn][Gg][Ee][Tt]|[Cc][Hh][Aa][Nn][Gg][0-9A-DF-Za-df-z-][0-9A-Za-z-][0-9A-Za-z-]*|[Cc][Hh][Aa][Nn][Gg][0-9A-DF-Za-df-z-]|[Cc][Hh][Aa][Nn][Gg]|[Cc][Hh][Aa][Nn][0-9A-FH-Za-fh-z-][0-9A-Za-z-][0-9A-Za-z-]*|[Cc][Hh][Aa][Nn][0-9A-FH-Za-fh-z-]|[Cc][Hh][Aa][Nn]|[Cc][Hh][Aa][0-9A-MO-Za-mo-z-][0-9A-Za-z-][0-9A-Za-z-]*|[Cc][Hh][Aa][0-9A-MO-Za-mo-z-]|[Cc][Hh][Aa]|[Cc][Hh][0-9B-Zb-z-][0-9A-Za-z-][0-9A-Za-z-]*|[Cc][Hh][0-9B-Zb-z-]|[Cc][Hh]|[Cc][0-9A-GI-Za-gi-z-]([0-9A-Za-z-][0-9A-Za-z-][0-9A-Za-z-]*|[0-9A-Za-z-]|())|[Cc][Hh][Aa][Nn][Gg][Ee][Tt][Yy][0-9A-OQ-Za-oq-z-][0-9A-Za-z-][0-9A-Za-z-]*|[Cc][Hh][Aa][Nn][Gg][Ee][Tt][Yy][0-9A-OQ-Za-oq-z-]|[Cc][Hh][Aa][Nn][Gg][Ee][Tt][Yy]|([Cc][Hh][Aa][Nn][Gg][Ee][Tt][Yy][Pp][Ee][0-9A-Za-z-][0-9A-Za-z-]|[Cc][Hh][Aa][Nn][Gg][Ee][Tt][Yy][Pp][0-9A-DF-Za-df-z-][0-9A-Za-z-])[0-9A-Za-z-]*|[Cc][Hh][Aa][Nn][Gg][Ee][Tt][Yy][Pp][Ee][0-9A-Za-z-]|[Cc][Hh][Aa][Nn][Gg][Ee][Tt][Yy][Pp][0-9A-DF-Za-df-z-]|[Cc][Hh][Aa][Nn][Gg][Ee][Tt][Yy][Pp]|[Cc][Hh][Aa][Nn][Gg][Ee][0-9A-SU-Za-su-z-][0-9A-Za-z-][0-9A-Za-z-]*|[Cc][Hh][Aa][Nn][Gg][Ee][0-9A-SU-Za-su-z-]|[Cc][Hh][Aa][Nn][Gg][Ee]|[Dd][Nn][0-9A-Za-z-][0-9A-Za-z-]([0-9A-Za-z-][0-9A-Za-z-]*|())|[Dd][0-9A-MO-Za-mo-z-][0-9A-Za-z-][0-9A-Za-z-][0-9A-Za-z-]*|[Dd][0-9A-MO-Za-mo-z-][0-9A-Za-z-]|[Ii][Nn][Cc][Ll][Uu][Dd](([Ee][0-9A-Za-z-]|[0-9A-DF-Za-df-z-])[0-9A-Za-z-]*|())|[Ii][Nn][Cc][Ll][Uu]([0-9A-CE-Za-ce-z-][0-9A-Za-z-]*|())|[Ii][Nn][Cc][Ll]([0-9A-TV-Za-tv-z-][0-9A-Za-z-]*|())|([Ii][Nn][Cc][0-9A-KM-Za-km-z-]|([Ii][Nn][0-9ABD-Zabd-z-]|([Ii][0-9A-MO-Za-mo-z-]|[ABE-HJ-Zabe-hj-z][0-9A-Za-z-])[0-9A-Za-z-])[0-9A-Za-z-])[0-9A-Za-z-]*|[Ii][Nn][Cc]|[Ii][Nn][0-9ABD-Zabd-z-]|([Ii][0-9A-MO-Za-mo-z-]|[ABE-HJ-Zabe-hj-z][0-9A-Za-z-])[0-9A-Za-z-]|[Ii][Nn]|[Ii][0-9A-MO-Za-mo-z-]|[ABE-HJ-Zabe-hj-z][0-9A-Za-z-]|[Ii]|[ABE-HJ-Zabe-hj-z]|[Dd]|[Dd][Nn][0-9A-Za-z-]|[Dd][0-9A-MO-Za-mo-z-]|[Cc])";
                    }
                  }
                  uses option-list2;
                }
                container delete {
                  augex:data-path "delete";
                  augex:value-yang-path "attr-type";
                  presence "Config entry.";
                  leaf attr-type {
                    mandatory true;
                    type string {
                      pattern "([0-9][0-9\\\\.]*)|([Cc][Hh][Aa][Nn][Gg][Ee][Tt][0-9A-XZa-xz-][0-9A-Za-z-][0-9A-Za-z-]*|[Cc][Hh][Aa][Nn][Gg][Ee][Tt][0-9A-XZa-xz-]|[Cc][Hh][Aa][Nn][Gg][Ee][Tt]|[Cc][Hh][Aa][Nn][Gg][0-9A-DF-Za-df-z-][0-9A-Za-z-][0-9A-Za-z-]*|[Cc][Hh][Aa][Nn][Gg][0-9A-DF-Za-df-z-]|[Cc][Hh][Aa][Nn][Gg]|[Cc][Hh][Aa][Nn][0-9A-FH-Za-fh-z-][0-9A-Za-z-][0-9A-Za-z-]*|[Cc][Hh][Aa][Nn][0-9A-FH-Za-fh-z-]|[Cc][Hh][Aa][Nn]|[Cc][Hh][Aa][0-9A-MO-Za-mo-z-][0-9A-Za-z-][0-9A-Za-z-]*|[Cc][Hh][Aa][0-9A-MO-Za-mo-z-]|[Cc][Hh][Aa]|[Cc][Hh][0-9B-Zb-z-][0-9A-Za-z-][0-9A-Za-z-]*|[Cc][Hh][0-9B-Zb-z-]|[Cc][Hh]|[Cc][0-9A-GI-Za-gi-z-]([0-9A-Za-z-][0-9A-Za-z-][0-9A-Za-z-]*|[0-9A-Za-z-]|())|[Cc][Hh][Aa][Nn][Gg][Ee][Tt][Yy][0-9A-OQ-Za-oq-z-][0-9A-Za-z-][0-9A-Za-z-]*|[Cc][Hh][Aa][Nn][Gg][Ee][Tt][Yy][0-9A-OQ-Za-oq-z-]|[Cc][Hh][Aa][Nn][Gg][Ee][Tt][Yy]|([Cc][Hh][Aa][Nn][Gg][Ee][Tt][Yy][Pp][Ee][0-9A-Za-z-][0-9A-Za-z-]|[Cc][Hh][Aa][Nn][Gg][Ee][Tt][Yy][Pp][0-9A-DF-Za-df-z-][0-9A-Za-z-])[0-9A-Za-z-]*|[Cc][Hh][Aa][Nn][Gg][Ee][Tt][Yy][Pp][Ee][0-9A-Za-z-]|[Cc][Hh][Aa][Nn][Gg][Ee][Tt][Yy][Pp][0-9A-DF-Za-df-z-]|[Cc][Hh][Aa][Nn][Gg][Ee][Tt][Yy][Pp]|[Cc][Hh][Aa][Nn][Gg][Ee][0-9A-SU-Za-su-z-][0-9A-Za-z-][0-9A-Za-z-]*|[Cc][Hh][Aa][Nn][Gg][Ee][0-9A-SU-Za-su-z-]|[Cc][Hh][Aa][Nn][Gg][Ee]|[Dd][Nn][0-9A-Za-z-][0-9A-Za-z-]([0-9A-Za-z-][0-9A-Za-z-]*|())|[Dd][0-9A-MO-Za-mo-z-][0-9A-Za-z-][0-9A-Za-z-][0-9A-Za-z-]*|[Dd][0-9A-MO-Za-mo-z-][0-9A-Za-z-]|[Ii][Nn][Cc][Ll][Uu][Dd](([Ee][0-9A-Za-z-]|[0-9A-DF-Za-df-z-])[0-9A-Za-z-]*|())|[Ii][Nn][Cc][Ll][Uu]([0-9A-CE-Za-ce-z-][0-9A-Za-z-]*|())|[Ii][Nn][Cc][Ll]([0-9A-TV-Za-tv-z-][0-9A-Za-z-]*|())|([Ii][Nn][Cc][0-9A-KM-Za-km-z-]|([Ii][Nn][0-9ABD-Zabd-z-]|([Ii][0-9A-MO-Za-mo-z-]|[ABE-HJ-Zabe-hj-z][0-9A-Za-z-])[0-9A-Za-z-])[0-9A-Za-z-])[0-9A-Za-z-]*|[Ii][Nn][Cc]|[Ii][Nn][0-9ABD-Zabd-z-]|([Ii][0-9A-MO-Za-mo-z-]|[ABE-HJ-Zabe-hj-z][0-9A-Za-z-])[0-9A-Za-z-]|[Ii][Nn]|[Ii][0-9A-MO-Za-mo-z-]|[ABE-HJ-Zabe-hj-z][0-9A-Za-z-]|[Ii]|[ABE-HJ-Zabe-hj-z]|[Dd]|[Dd][Nn][0-9A-Za-z-]|[Dd][0-9A-MO-Za-mo-z-]|[Cc])";
                    }
                  }
                  uses option-list2;
                }
                container replace {
                  augex:data-path "replace";
                  augex:value-yang-path "attr-type";
                  presence "Config entry.";
                  leaf attr-type {
                    mandatory true;
                    type string {
                      pattern "([0-9][0-9\\\\.]*)|([Cc][Hh][Aa][Nn][Gg][Ee][Tt][0-9A-XZa-xz-][0-9A-Za-z-][0-9A-Za-z-]*|[Cc][Hh][Aa][Nn][Gg][Ee][Tt][0-9A-XZa-xz-]|[Cc][Hh][Aa][Nn][Gg][Ee][Tt]|[Cc][Hh][Aa][Nn][Gg][0-9A-DF-Za-df-z-][0-9A-Za-z-][0-9A-Za-z-]*|[Cc][Hh][Aa][Nn][Gg][0-9A-DF-Za-df-z-]|[Cc][Hh][Aa][Nn][Gg]|[Cc][Hh][Aa][Nn][0-9A-FH-Za-fh-z-][0-9A-Za-z-][0-9A-Za-z-]*|[Cc][Hh][Aa][Nn][0-9A-FH-Za-fh-z-]|[Cc][Hh][Aa][Nn]|[Cc][Hh][Aa][0-9A-MO-Za-mo-z-][0-9A-Za-z-][0-9A-Za-z-]*|[Cc][Hh][Aa][0-9A-MO-Za-mo-z-]|[Cc][Hh][Aa]|[Cc][Hh][0-9B-Zb-z-][0-9A-Za-z-][0-9A-Za-z-]*|[Cc][Hh][0-9B-Zb-z-]|[Cc][Hh]|[Cc][0-9A-GI-Za-gi-z-]([0-9A-Za-z-][0-9A-Za-z-][0-9A-Za-z-]*|[0-9A-Za-z-]|())|[Cc][Hh][Aa][Nn][Gg][Ee][Tt][Yy][0-9A-OQ-Za-oq-z-][0-9A-Za-z-][0-9A-Za-z-]*|[Cc][Hh][Aa][Nn][Gg][Ee][Tt][Yy][0-9A-OQ-Za-oq-z-]|[Cc][Hh][Aa][Nn][Gg][Ee][Tt][Yy]|([Cc][Hh][Aa][Nn][Gg][Ee][Tt][Yy][Pp][Ee][0-9A-Za-z-][0-9A-Za-z-]|[Cc][Hh][Aa][Nn][Gg][Ee][Tt][Yy][Pp][0-9A-DF-Za-df-z-][0-9A-Za-z-])[0-9A-Za-z-]*|[Cc][Hh][Aa][Nn][Gg][Ee][Tt][Yy][Pp][Ee][0-9A-Za-z-]|[Cc][Hh][Aa][Nn][Gg][Ee][Tt][Yy][Pp][0-9A-DF-Za-df-z-]|[Cc][Hh][Aa][Nn][Gg][Ee][Tt][Yy][Pp]|[Cc][Hh][Aa][Nn][Gg][Ee][0-9A-SU-Za-su-z-][0-9A-Za-z-][0-9A-Za-z-]*|[Cc][Hh][Aa][Nn][Gg][Ee][0-9A-SU-Za-su-z-]|[Cc][Hh][Aa][Nn][Gg][Ee]|[Dd][Nn][0-9A-Za-z-][0-9A-Za-z-]([0-9A-Za-z-][0-9A-Za-z-]*|())|[Dd][0-9A-MO-Za-mo-z-][0-9A-Za-z-][0-9A-Za-z-][0-9A-Za-z-]*|[Dd][0-9A-MO-Za-mo-z-][0-9A-Za-z-]|[Ii][Nn][Cc][Ll][Uu][Dd](([Ee][0-9A-Za-z-]|[0-9A-DF-Za-df-z-])[0-9A-Za-z-]*|())|[Ii][Nn][Cc][Ll][Uu]([0-9A-CE-Za-ce-z-][0-9A-Za-z-]*|())|[Ii][Nn][Cc][Ll]([0-9A-TV-Za-tv-z-][0-9A-Za-z-]*|())|([Ii][Nn][Cc][0-9A-KM-Za-km-z-]|([Ii][Nn][0-9ABD-Zabd-z-]|([Ii][0-9A-MO-Za-mo-z-]|[ABE-HJ-Zabe-hj-z][0-9A-Za-z-])[0-9A-Za-z-])[0-9A-Za-z-])[0-9A-Za-z-]*|[Ii][Nn][Cc]|[Ii][Nn][0-9ABD-Zabd-z-]|([Ii][0-9A-MO-Za-mo-z-]|[ABE-HJ-Zabe-hj-z][0-9A-Za-z-])[0-9A-Za-z-]|[Ii][Nn]|[Ii][0-9A-MO-Za-mo-z-]|[ABE-HJ-Zabe-hj-z][0-9A-Za-z-]|[Ii]|[ABE-HJ-Zabe-hj-z]|[Dd]|[Dd][Nn][0-9A-Za-z-]|[Dd][0-9A-MO-Za-mo-z-]|[Cc])";
                    }
                  }
                  uses option-list2;
                }
              }
            }
            list change-modrdn {
              key "_id";
              when "re-match(../change-type/value, 'modr?dn')";
              ordered-by user;
              leaf _id {
                type uint64;
                description
                  "Implicitly generated list key to maintain the order of the augeas data.";
              }
              choice ch-change-modrdn {
                mandatory true;
                container newrdn {
                  augex:data-path "newrdn";
                  augex:value-yang-path "value";
                  presence "Config entry.";
                  choice ch-newrdn {
                    mandatory true;
                    leaf value {
                      type string {
                        pattern "([^ \t\n:<][^\n]*)((\n[ \t]+[^ \t\n][^\n]*)*)";
                      }
                    }
                    leaf base64 {
                      type string {
                        pattern "([a-zA-Z0-9=+]+)(((\n[ \t]+)([a-zA-Z0-9=+]+))*)";
                      }
                      augex:data-path "@base64";
                    }
                  }
                }
                container newsuperior {
                  augex:data-path "newsuperior";
                  augex:value-yang-path "value";
                  presence "Config entry.";
                  choice ch-newsuperior {
                    mandatory true;
                    leaf value {
                      type string {
                        pattern "([^ \t\n:<][^\n]*)((\n[ \t]+[^ \t\n][^\n]*)*)";
                      }
                    }
                    leaf base64 {
                      type string {
                        pattern "([a-zA-Z0-9=+]+)(((\n[ \t]+)([a-zA-Z0-9=+]+))*)";
                      }
                      augex:data-path "@base64";
                    }
                  }
                }
                leaf deleteoldrdn {
                  type string {
                    pattern "0|1";
                  }
                  augex:data-path "deleteoldrdn";
                }
              }
            }
          }
        }
        list sep-record3 {
          key "_id";
          ordered-by user;
          leaf _id {
            type uint64;
            description
              "Implicitly generated list key to maintain the order of the augeas data.";
          }
          uses include;
        }
      }
    }
  }
}
