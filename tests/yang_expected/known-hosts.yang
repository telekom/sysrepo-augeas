module known-hosts {
  yang-version 1.1;
  namespace "aug:known-hosts";
  prefix aug;

  import augeas-extension {
    prefix augex;
  }

  augex:augeas-mod-name "Known_Hosts";

  list known-hosts {
    key "config-file";
    leaf config-file {
      type string;
    }
    list entry-list {
      key "_seq";
      ordered-by user;
      augex:data-path "$$";
      augex:value-yang-path "neg1";
      leaf _seq {
        type uint64;
        description
          "Key contains some unique value. The order is based on the actual order of list instances.";
      }
      leaf marker {
        type string {
          pattern "@(revoked|cert-authority)";
        }
        augex:data-path "$$";
      }
      leaf neg1 {
        mandatory true;
        type string {
          pattern "[^,# \n\t]+";
        }
      }
      list alias-list {
        key "_id";
        ordered-by user;
        leaf _id {
          type uint64;
          description
            "Implicitly generated list key to maintain the order of the augeas data.";
        }
        leaf alias {
          mandatory true;
          type string {
            pattern "[^,# \n\t]+";
          }
          augex:data-path "alias";
        }
      }
      leaf type {
        mandatory true;
        type string {
          pattern "[^,# \n\t]+";
        }
        augex:data-path "type";
      }
      leaf key {
        mandatory true;
        type string {
          pattern "[^,# \n\t]+";
        }
        augex:data-path "key";
      }
    }
  }
}
