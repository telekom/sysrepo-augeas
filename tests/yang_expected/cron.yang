module cron {
  yang-version 1.1;
  namespace "aug:cron";
  prefix aug;

  import augeas-extension {
    prefix augex;
  }

  augex:augeas-mod-name "Cron";

  list cron {
    key "config-file";
    leaf config-file {
      type string;
    }
    list config-entries {
      key "_id";
      ordered-by user;
      leaf _id {
        type uint64;
        description
          "Implicitly generated list key to maintain the order of the augeas data.";
      }
      choice ch-config-entries {
        mandatory true;
        container shellvar {
          augex:data-path "$$";
          augex:value-yang-path "value";
          presence "Config entry.";
          leaf label {
            mandatory true;
            type string {
              pattern "[A-Za-z1-9_-]+(\\[[0-9]+\\])?";
              pattern "entry" {
                modifier invert-match;
              }
            }
          }
          leaf value {
            mandatory true;
            type string {
              pattern "[^\n]*[^ \t\n]";
            }
          }
        }
        container entry {
          augex:data-path "entry";
          augex:value-yang-path "space-in";
          presence "Config entry.";
          leaf prefix {
            type string {
              pattern "-";
            }
            augex:data-path "prefix";
          }
          choice ch-entry {
            mandatory true;
            container time {
              augex:data-path "time";
              presence "Config entry.";
              leaf minute {
                mandatory true;
                type string {
                  pattern "[0-9*][0-9/,*-]*";
                }
                augex:data-path "minute";
              }
              leaf hour {
                mandatory true;
                type string {
                  pattern "[0-9*][0-9/,*-]*";
                }
                augex:data-path "hour";
              }
              leaf dayofmonth {
                mandatory true;
                type string {
                  pattern "[0-9*][0-9/,*-]*";
                }
                augex:data-path "dayofmonth";
              }
              leaf month {
                mandatory true;
                type string {
                  pattern "(([0-9*][0-9/,*-]*)|([A-Za-z]{3}))(((-)(([0-9*][0-9/,*-]*)|([A-Za-z]{3}))){0,1})";
                }
                augex:data-path "month";
              }
              leaf dayofweek {
                mandatory true;
                type string {
                  pattern "(([0-9*][0-9/,*-]*)|([A-Za-z]{3}))(((-)(([0-9*][0-9/,*-]*)|([A-Za-z]{3}))){0,1})";
                }
                augex:data-path "dayofweek";
              }
            }
            leaf schedule {
              type string {
                pattern "(((((((reboot)|(yearly))|(annually))|(monthly))|(weekly))|(daily))|(midnight))|(hourly)";
              }
              augex:data-path "schedule";
            }
          }
          leaf user {
            mandatory true;
            type string {
              pattern "[A-Za-z0-9_.-]+";
            }
            augex:data-path "user";
          }
          leaf space-in {
            mandatory true;
            type string {
              pattern "[^ \t\n].*[^ \t\n]|[^ \t\n]";
            }
          }
        }
      }
    }
  }
}
