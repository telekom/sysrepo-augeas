module php {
  yang-version 1.1;
  namespace "aug:php";
  prefix aug;

  import augeas-extension {
    prefix augex;
  }

  augex:augeas-mod-name "PHP";

  grouping record-anon {
    list config-entries {
      key "_id";
      ordered-by user;
      leaf _id {
        type uint64;
        description
          "Implicitly generated list key to maintain the order of the augeas data.";
      }
      container node {
        augex:data-path "$$";
        augex:value-yang-path "value";
        presence "Config entry.";
        leaf label {
          mandatory true;
          type string {
            pattern "([A-Za-z][A-Za-z0-9._-]*)((((\\[)([A-Za-z][A-Za-z0-9._-]*))(\\])){0,1})";
          }
        }
        leaf value {
          type union {
            type string {
              pattern "([^\t\n \"#;])((((([^\n#;])+)*)([^\t\n \"#;])){0,1})";
            }
            type string {
              pattern "(([^\"\n]*)(([;#])+))([^\"\n]*)";
            }
          }
        }
      }
    }
  }
  list php {
    key "config-file";
    leaf config-file {
      type string;
    }
    container anon {
      augex:data-path ".anon";
      presence "Config entry.";
      uses record-anon;
    }
    list record-list {
      key "_id";
      ordered-by user;
      leaf _id {
        type uint64;
        description
          "Implicitly generated list key to maintain the order of the augeas data.";
      }
      container record {
        augex:data-path "$$";
        presence "Config entry.";
        leaf label {
          mandatory true;
          type string {
            pattern "#[^\\]\n/c]([^\\]\n/][^\\]\n/]*|())|(#comment[^\\]\n/][^\\]\n/]|#commen[^\\]\n/t][^\\]\n/])[^\\]\n/]*|#comment[^\\]\n/]|#commen[^\\]\n/t]|#commen|#comme[^\\]\n/n][^\\]\n/][^\\]\n/]*|#comme[^\\]\n/n]|#comme|#com[^\\]\n/m][^\\]\n/][^\\]\n/]*|#com[^\\]\n/m]|#com|#co[^\\]\n/m][^\\]\n/][^\\]\n/]*|#co[^\\]\n/m]|#co|#comm[^\\]\n/e][^\\]\n/][^\\]\n/]*|#comm[^\\]\n/e]|#comm|#c[^\\]\n/o][^\\]\n/][^\\]\n/]*|#c[^\\]\n/o]|#c|\\.ano((n[^\\]\n/]|[^\\]\n/n])[^\\]\n/]*|())|\\.an([^\\]\n/o][^\\]\n/]*|())|(\\.a[^\\]\n/n]|(\\.[^\\]\n/a]|[^\\]\n#./][^\\]\n/])[^\\]\n/])[^\\]\n/]*|\\.a|\\.[^\\]\n/a]|[^\\]\n#./][^\\]\n/]|[^\\]\n#./]|\\.|#";
          }
        }
        uses record-anon;
      }
    }
  }
}
