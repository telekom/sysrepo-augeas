module iptables {
  yang-version 1.1;
  namespace "aug:iptables";
  prefix aug;

  import augeas-extension {
    prefix augex;
  }

  augex:augeas-mod-name "Iptables";

  grouping ipt-match {
    list ipt-match {
      key "_id";
      ordered-by user;
      leaf _id {
        type uint64;
        description
          "Implicitly generated list key to maintain the order of the augeas data.";
      }
      choice ch-ipt-match {
        mandatory true;
        container protocol {
          augex:data-path "protocol";
          augex:value-yang-path "value";
          presence "Config entry.";
          leaf not {
            type empty;
            augex:data-path "not";
          }
          leaf value {
            mandatory true;
            type string {
              pattern "(![ \t]*)?[^ \t\n!-][^ \t\n]*";
            }
          }
        }
        container source {
          augex:data-path "source";
          augex:value-yang-path "value";
          presence "Config entry.";
          leaf not {
            type empty;
            augex:data-path "not";
          }
          leaf value {
            mandatory true;
            type string {
              pattern "(![ \t]*)?[^ \t\n!-][^ \t\n]*";
            }
          }
        }
        container destination {
          augex:data-path "destination";
          augex:value-yang-path "value";
          presence "Config entry.";
          leaf not {
            type empty;
            augex:data-path "not";
          }
          leaf value {
            mandatory true;
            type string {
              pattern "(![ \t]*)?[^ \t\n!-][^ \t\n]*";
            }
          }
        }
        leaf jump {
          type string {
            pattern "(![ \t]*)?[^ \t\n!-][^ \t\n]*";
          }
          augex:data-path "jump";
        }
        leaf goto {
          type string {
            pattern "(![ \t]*)?[^ \t\n!-][^ \t\n]*";
          }
          augex:data-path "goto";
        }
        container in-interface {
          augex:data-path "in-interface";
          augex:value-yang-path "value";
          presence "Config entry.";
          leaf not {
            type empty;
            augex:data-path "not";
          }
          leaf value {
            mandatory true;
            type string {
              pattern "(![ \t]*)?[^ \t\n!-][^ \t\n]*";
            }
          }
        }
        container out-interface {
          augex:data-path "out-interface";
          augex:value-yang-path "value";
          presence "Config entry.";
          leaf not {
            type empty;
            augex:data-path "not";
          }
          leaf value {
            mandatory true;
            type string {
              pattern "(![ \t]*)?[^ \t\n!-][^ \t\n]*";
            }
          }
        }
        container fragment {
          augex:data-path "fragment";
          augex:value-yang-path "value";
          presence "Config entry.";
          leaf not {
            type empty;
            augex:data-path "not";
          }
          leaf value {
            mandatory true;
            type string {
              pattern "(![ \t]*)?[^ \t\n!-][^ \t\n]*";
            }
          }
        }
        leaf match {
          type string {
            pattern "(![ \t]*)?[^ \t\n!-][^ \t\n]*";
          }
          augex:data-path "match";
        }
        container tcp-flags {
          augex:data-path "tcp-flags";
          presence "Config entry.";
          list mask-list {
            key "_id";
            min-elements 1;
            ordered-by user;
            leaf _id {
              type uint64;
              description
                "Implicitly generated list key to maintain the order of the augeas data.";
            }
            leaf mask {
              mandatory true;
              type string {
                pattern "SYN|ACK|FIN|RST|URG|PSH|ALL|NONE";
              }
              augex:data-path "mask";
            }
          }
          list set-list {
            key "_id";
            min-elements 1;
            ordered-by user;
            leaf _id {
              type uint64;
              description
                "Implicitly generated list key to maintain the order of the augeas data.";
            }
            leaf set {
              mandatory true;
              type string {
                pattern "SYN|ACK|FIN|RST|URG|PSH|ALL|NONE";
              }
              augex:data-path "set";
            }
          }
        }
        container any-param {
          augex:data-path "$$";
          augex:value-yang-path "value";
          presence "Config entry.";
          leaf label {
            mandatory true;
            type string {
              pattern "[a-zA-Z-][a-zA-Z0-9-]+";
              pattern "protocol|source|destination|jump|goto|in-interface|out-interface|fragment|match|tcp-flags" {
                modifier invert-match;
              }
            }
          }
          leaf not {
            type empty;
            augex:data-path "not";
          }
          leaf value {
            type string {
              pattern "([^\" \t\n!-][^ \t\n]*)|\"([^\"\\\\\n]|\\\\.)*\"";
            }
          }
        }
      }
    }
  }
  list iptables {
    key "config-file";
    leaf config-file {
      type string;
    }
    list table-list {
      key "_id";
      ordered-by user;
      leaf _id {
        type uint64;
        description
          "Implicitly generated list key to maintain the order of the augeas data.";
      }
      container table {
        augex:data-path "table";
        augex:value-yang-path "value";
        presence "Config entry.";
        leaf value {
          mandatory true;
          type string {
            pattern "[a-z]+";
          }
        }
        list config-entries {
          key "_id";
          ordered-by user;
          leaf _id {
            type uint64;
            description
              "Implicitly generated list key to maintain the order of the augeas data.";
          }
          choice ch-config-entries {
            mandatory true;
            container chain {
              augex:data-path "chain";
              augex:value-yang-path "chain-name";
              presence "Config entry.";
              leaf chain-name {
                mandatory true;
                type string {
                  pattern "[A-Za-z0-9_-]+";
                }
              }
              leaf policy {
                mandatory true;
                type string {
                  pattern "ACCEPT|DROP|REJECT|-";
                }
                augex:data-path "policy";
              }
            }
            container append {
              augex:data-path "append";
              augex:value-yang-path "chain-name";
              presence "Config entry.";
              leaf chain-name {
                mandatory true;
                type string {
                  pattern "[A-Za-z0-9_-]+";
                }
              }
              uses ipt-match;
            }
            container insert {
              augex:data-path "insert";
              augex:value-yang-path "chain-name";
              presence "Config entry.";
              leaf chain-name {
                mandatory true;
                type string {
                  pattern "[A-Za-z0-9_-]+";
                }
              }
              uses ipt-match;
            }
          }
        }
      }
    }
  }
}
