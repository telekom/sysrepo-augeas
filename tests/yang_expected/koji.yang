module koji {
  yang-version 1.1;
  namespace "aug:koji";
  prefix aug;

  import augeas-extension {
    prefix augex;
  }

  augex:augeas-mod-name "Koji";

  grouping entry-list {
    list entry-list {
      key "_id";
      ordered-by user;
      leaf _id {
        type uint64;
        description
          "Implicitly generated list key to maintain the order of the augeas data.";
      }
      container entry {
        augex:data-path "$$";
        augex:value-yang-path "value";
        presence "Config entry.";
        leaf entry {
          mandatory true;
          type string {
            pattern "[A-Za-z][A-Za-z0-9._-]*";
          }
        }
        leaf value {
          type union {
            type string {
              pattern "(((([^\t\n \"#;])+)((((([^\n#;])+)*)(([^\t\n \"#;])+)){0,1}))(((\n[ \t]+)((([^\t\n \"#;])+)((((([^\n#;])+)*)(([^\t\n \"#;])+)){0,1})))*))|(((\n[ \t]+)((([^\t\n \"#;])+)((((([^\n#;])+)*)(([^\t\n \"#;])+)){0,1})))+)";
            }
            type string {
              pattern "(((([^\"\n]*)(([;#])+))([^\"\n]*))(((\n[ \t]+)((([^\"\n]*)(([;#])+))([^\"\n]*)))*))|(((\n[ \t]+)((([^\"\n]*)(([;#])+))([^\"\n]*)))+)";
            }
          }
        }
      }
    }
  }
  list koji {
    key "config-file";
    leaf config-file {
      type string;
    }
    container section {
      augex:data-path "section";
      augex:value-yang-path "value";
      presence "Config entry.";
      leaf value {
        mandatory true;
        type enumeration {
          enum ".anon";
        }
      }
      uses entry-list;
    }
    list section-list {
      key "_id";
      ordered-by user;
      leaf _id {
        type uint64;
        description
          "Implicitly generated list key to maintain the order of the augeas data.";
      }
      container section {
        augex:data-path "section";
        augex:value-yang-path "value";
        presence "Config entry.";
        leaf value {
          mandatory true;
          type string {
            pattern "\\.ano((n[^\\]\n]|[^\\]\nn])[^\\]\n]*|())|\\.an([^\\]\no][^\\]\n]*|())|\\.a([^\\]\nn][^\\]\n]*|())|(\\.[^\\]\na]|[^\\]\n.][^\\]\n])[^\\]\n]*|\\.|[^\\]\n.]";
          }
        }
        uses entry-list;
      }
    }
  }
}
