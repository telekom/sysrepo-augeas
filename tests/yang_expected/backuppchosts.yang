module backuppchosts {
  yang-version 1.1;
  namespace "aug:backuppchosts";
  prefix aug;

  import augeas-extension {
    prefix augex;
  }

  augex:augeas-mod-name "BackupPCHosts";

  list backuppchosts {
    key "config-file";
    leaf config-file {
      type string;
    }
    list host-list {
      key "_seq";
      ordered-by user;
      augex:data-path "$$";
      leaf _seq {
        type uint64;
        description
          "Key contains some unique value. The order is based on the actual order of list instances.";
      }
      leaf host {
        mandatory true;
        type string {
          pattern "[^#, \n\t/]+";
        }
        augex:data-path "host";
      }
      leaf dhcp {
        mandatory true;
        type string {
          pattern "[^#, \n\t/]+";
        }
        augex:data-path "dhcp";
      }
      leaf user {
        mandatory true;
        type string {
          pattern "[^#, \n\t/]+";
        }
        augex:data-path "user";
      }
      list moreusers-list {
        key "_id";
        ordered-by user;
        leaf _id {
          type uint64;
          description
            "Implicitly generated list key to maintain the order of the augeas data.";
        }
        leaf moreusers {
          mandatory true;
          type string {
            pattern "[^#, \n\t/]+";
          }
          augex:data-path "moreusers";
        }
      }
    }
  }
}
