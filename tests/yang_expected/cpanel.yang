module cpanel {
  yang-version 1.1;
  namespace "aug:cpanel";
  prefix aug;

  import augeas-extension {
    prefix augex;
  }

  augex:augeas-mod-name "CPanel";

  list cpanel {
    key "config-file";
    leaf config-file {
      type string;
    }
    list kv-list {
      key "_id";
      ordered-by user;
      leaf _id {
        type uint64;
        description
          "Implicitly generated list key to maintain the order of the augeas data.";
      }
      container kv {
        augex:data-path "$$";
        augex:value-yang-path "value";
        presence "Config entry.";
        leaf label {
          mandatory true;
          type string {
            pattern "[A-Za-z0-9:_.-]+";
          }
        }
        leaf value {
          type union {
            type string {
              length 0;
            }
            type string {
              pattern "([^ \t\n].*[^ \t\n]|[^ \t\n]){0,1}";
            }
          }
        }
      }
    }
  }
}
