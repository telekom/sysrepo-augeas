module csv {
  yang-version 1.1;
  namespace "aug:csv";
  prefix aug;

  import augeas-extension {
    prefix augex;
  }

  augex:augeas-mod-name "CSV";

  list csv {
    key "config-file";
    leaf config-file {
      type string;
    }
    list entry-list {
      key "_seq";
      ordered-by user;
      augex:data-path "$$";
      leaf _seq {
        type uint64;
        description
          "Key contains some unique value. The order is based on the actual order of list instances.";
      }
      list field-list {
        key "_seq";
        min-elements 1;
        ordered-by user;
        augex:data-path "$$";
        augex:value-yang-path "value";
        leaf _seq {
          type uint64;
          description
            "Key contains some unique value. The order is based on the actual order of list instances.";
        }
        leaf value {
          type union {
            type string {
              pattern "([^\n\"#;])*";
            }
            type string {
              pattern "(\"[^\"#]*\")+";
            }
          }
        }
      }
    }
  }
}
