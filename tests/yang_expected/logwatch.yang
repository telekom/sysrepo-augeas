module logwatch {
  yang-version 1.1;
  namespace "aug:logwatch";
  prefix aug;

  import augeas-extension {
    prefix augex;
  }

  augex:augeas-mod-name "Logwatch";

  list logwatch {
    key "config-file";
    leaf config-file {
      type string;
    }
    list entry-list {
      key "_id";
      ordered-by user;
      leaf _id {
        type uint64;
        description
          "Implicitly generated list key to maintain the order of the augeas data.";
      }
      container entry {
        augex:data-path "$$";
        augex:value-yang-path "sto-to-eol";
        presence "Config entry.";
        leaf entry {
          mandatory true;
          type string {
            pattern "[A-Za-z0-9._-]+";
          }
        }
        leaf sto-to-eol {
          mandatory true;
          type string {
            pattern "[^ \t\n].*[^ \t\n]|[^ \t\n]";
          }
        }
      }
    }
  }
}
