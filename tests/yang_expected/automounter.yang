module automounter {
  yang-version 1.1;
  namespace "aug:automounter";
  prefix aug;

  import augeas-extension {
    prefix augex;
  }

  augex:augeas-mod-name "Automounter";

  grouping opt-list {
    list opt-list {
      key "_id";
      ordered-by user;
      leaf _id {
        type uint64;
        description
          "Implicitly generated list key to maintain the order of the augeas data.";
      }
      container opt {
        augex:data-path "opt";
        augex:value-yang-path "optlabel";
        presence "Config entry.";
        leaf optlabel {
          mandatory true;
          type string {
            pattern "[^,#:\\\\(\\\\)= \n\t]+";
          }
        }
        leaf value {
          type string {
            pattern "[^,# \n\t]+";
          }
          augex:data-path "value";
        }
      }
    }
  }
  grouping location-list {
    list location-list {
      key "_seq";
      min-elements 1;
      ordered-by user;
      augex:data-path "$$";
      leaf _seq {
        type uint64;
        description
          "Key contains some unique value. The order is based on the actual order of list instances.";
      }
      list entry-host-list {
        key "_id";
        ordered-by user;
        leaf _id {
          type uint64;
          description
            "Implicitly generated list key to maintain the order of the augeas data.";
        }
        container host {
          augex:data-path "host";
          augex:value-yang-path "hostname";
          presence "Config entry.";
          leaf hostname {
            mandatory true;
            type string {
              pattern "[^-:#\\\\(\\\\), \n\t][^:#\\\\(\\\\), \n\t]*";
            }
          }
          leaf weight {
            type uint64;
            augex:data-path "weight";
          }
        }
      }
      leaf path {
        mandatory true;
        type string {
          pattern "[^-+#: \t\n][^#: \t\n]*";
        }
        augex:data-path "path";
      }
    }
  }
  list automounter {
    key "config-file";
    leaf config-file {
      type string;
    }
    list entry-list {
      key "_seq";
      ordered-by user;
      augex:data-path "$$";
      augex:value-yang-path "value";
      leaf _seq {
        type uint64;
        description
          "Key contains some unique value. The order is based on the actual order of list instances.";
      }
      leaf value {
        mandatory true;
        type union {
          type string {
            pattern "[^-+#: \t\n][^#: \t\n]*";
          }
          type string {
            pattern "\\+";
          }
        }
      }
      choice ch-entry-list {
        mandatory true;
        case opt-list {
          when "re-match(value, '[^-+#: \t\n][^#: \t\n]*')";
          uses opt-list;
          choice ch-opt-list {
            mandatory true;
            container location {
              augex:data-path "location";
              presence "Config entry.";
              uses location-list;
            }
            container mount {
              augex:data-path "mount";
              presence "Config entry.";
              list mount-list {
                key "_seq";
                min-elements 1;
                ordered-by user;
                augex:data-path "$$";
                augex:value-yang-path "entry-mkey";
                leaf _seq {
                  type uint64;
                  description
                    "Key contains some unique value. The order is based on the actual order of list instances.";
                }
                leaf entry-mkey {
                  mandatory true;
                  type string {
                    pattern "[^-+#: \t\n][^#: \t\n]*";
                  }
                }
                uses opt-list;
                container location {
                  augex:data-path "location";
                  presence "Config entry.";
                  uses location-list;
                }
              }
            }
          }
        }
        leaf map {
          type string {
            pattern "[^: \t\n]+";
          }
          augex:data-path "map";
          when "../value='+'";
        }
      }
    }
  }
}
