module ntp {
  yang-version 1.1;
  namespace "aug:ntp";
  prefix aug;

  import augeas-extension {
    prefix augex;
  }

  augex:augeas-mod-name "Ntp";

  grouping command-record {
    list config-entries {
      key "_id";
      ordered-by user;
      leaf _id {
        type uint64;
        description
          "Implicitly generated list key to maintain the order of the augeas data.";
      }
      choice ch-config-entries {
        mandatory true;
        leaf minpoll {
          type string {
            pattern "[^,# \n\t]+";
          }
          augex:data-path "minpoll";
        }
        leaf maxpoll {
          type string {
            pattern "[^,# \n\t]+";
          }
          augex:data-path "maxpoll";
        }
        leaf ttl {
          type string {
            pattern "[^,# \n\t]+";
          }
          augex:data-path "ttl";
        }
        leaf version {
          type string {
            pattern "[^,# \n\t]+";
          }
          augex:data-path "version";
        }
        leaf key {
          type string {
            pattern "[^,# \n\t]+";
          }
          augex:data-path "key";
        }
        leaf autokey {
          type empty;
          augex:data-path "autokey";
        }
        leaf burst {
          type empty;
          augex:data-path "burst";
        }
        leaf iburst {
          type empty;
          augex:data-path "iburst";
        }
        leaf noselect {
          type empty;
          augex:data-path "noselect";
        }
        leaf preempt {
          type empty;
          augex:data-path "preempt";
        }
        leaf prefer {
          type empty;
          augex:data-path "prefer";
        }
        leaf true {
          type empty;
          augex:data-path "true";
        }
        leaf dynamic {
          type empty;
          augex:data-path "dynamic";
        }
      }
    }
  }
  grouping flag-list {
    list flag-list {
      key "_id";
      ordered-by user;
      leaf _id {
        type uint64;
        description
          "Implicitly generated list key to maintain the order of the augeas data.";
      }
      leaf flag {
        mandatory true;
        type string {
          pattern "auth|bclient|calibrate|kernel|monitor|ntp|pps|stats";
        }
        augex:data-path "flag";
      }
    }
  }
  list ntp {
    key "config-file";
    leaf config-file {
      type string;
    }
    list config-entries {
      key "_id";
      ordered-by user;
      leaf _id {
        type uint64;
        description
          "Implicitly generated list key to maintain the order of the augeas data.";
      }
      choice ch-config-entries {
        mandatory true;
        container pool {
          augex:data-path "pool";
          augex:value-yang-path "word";
          presence "Config entry.";
          leaf word {
            mandatory true;
            type string {
              pattern "[^,# \n\t]+";
            }
          }
          uses command-record;
        }
        container server {
          augex:data-path "server";
          augex:value-yang-path "word";
          presence "Config entry.";
          leaf word {
            mandatory true;
            type string {
              pattern "[^,# \n\t]+";
            }
          }
          uses command-record;
        }
        container peer {
          augex:data-path "peer";
          augex:value-yang-path "word";
          presence "Config entry.";
          leaf word {
            mandatory true;
            type string {
              pattern "[^,# \n\t]+";
            }
          }
          uses command-record;
        }
        container broadcast {
          augex:data-path "broadcast";
          augex:value-yang-path "word";
          presence "Config entry.";
          leaf word {
            mandatory true;
            type string {
              pattern "[^,# \n\t]+";
            }
          }
          uses command-record;
        }
        container manycastclient {
          augex:data-path "manycastclient";
          augex:value-yang-path "word";
          presence "Config entry.";
          leaf word {
            mandatory true;
            type string {
              pattern "[^,# \n\t]+";
            }
          }
          uses command-record;
        }
        container multicastclient {
          augex:data-path "multicastclient";
          augex:value-yang-path "word";
          presence "Config entry.";
          leaf word {
            mandatory true;
            type string {
              pattern "[^,# \n\t]+";
            }
          }
          uses command-record;
        }
        container manycastserver {
          augex:data-path "manycastserver";
          augex:value-yang-path "word";
          presence "Config entry.";
          leaf word {
            mandatory true;
            type string {
              pattern "[^,# \n\t]+";
            }
          }
          uses command-record;
        }
        container fudge {
          augex:data-path "fudge";
          augex:value-yang-path "word";
          presence "Config entry.";
          leaf word {
            mandatory true;
            type string {
              pattern "[^,# \n\t]+";
            }
          }
          choice ch-fudge {
            mandatory true;
            leaf refid {
              type string {
                pattern "[^,# \n\t]+";
              }
              augex:data-path "refid";
            }
            leaf stratum {
              type string {
                pattern "[^,# \n\t]+";
              }
              augex:data-path "stratum";
            }
          }
        }
        container restrict {
          augex:data-path "restrict";
          augex:value-yang-path "value";
          presence "Config entry.";
          choice ch-restrict {
            leaf ipv6 {
              type empty;
              augex:data-path "ipv6";
            }
            leaf ipv4 {
              type empty;
              augex:data-path "ipv4";
            }
          }
          leaf value {
            mandatory true;
            type string {
              pattern "[^,# \n\t-][^,# \n\t]*";
            }
          }
          list action-list {
            key "_id";
            ordered-by user;
            leaf _id {
              type uint64;
              description
                "Implicitly generated list key to maintain the order of the augeas data.";
            }
            leaf action {
              mandatory true;
              type string {
                pattern "[^,# \n\t-][^,# \n\t]*";
              }
              augex:data-path "action";
            }
          }
        }
        leaf broadcastdelay {
          type string {
            pattern "[0-9]+([.,][0-9]+)?";
          }
          augex:data-path "broadcastdelay";
        }
        container enable {
          augex:data-path "enable";
          presence "Config entry.";
          uses flag-list;
        }
        container disable {
          augex:data-path "disable";
          presence "Config entry.";
          uses flag-list;
        }
        leaf driftfile {
          type string {
            pattern "[^,# \n\t]+";
          }
          augex:data-path "driftfile";
        }
        leaf leapfile {
          type string {
            pattern "[^,# \n\t]+";
          }
          augex:data-path "leapfile";
        }
        leaf logfile {
          type string {
            pattern "[^,# \n\t]+";
          }
          augex:data-path "logfile";
        }
        leaf includefile {
          type string {
            pattern "[^,# \n\t]+";
          }
          augex:data-path "includefile";
        }
        leaf statsdir {
          type string {
            pattern "[^,# \n\t]+";
          }
          augex:data-path "statsdir";
        }
        leaf ntpsigndsocket {
          type string {
            pattern "[^,# \n\t]+";
          }
          augex:data-path "ntpsigndsocket";
        }
        container statistics {
          augex:data-path "statistics";
          presence "Config entry.";
          list statistics-opts {
            key "_id";
            ordered-by user;
            leaf _id {
              type uint64;
              description
                "Implicitly generated list key to maintain the order of the augeas data.";
            }
            choice ch-statistics-opts {
              mandatory true;
              leaf loopstats {
                type empty;
                augex:data-path "loopstats";
              }
              leaf peerstats {
                type empty;
                augex:data-path "peerstats";
              }
              leaf clockstats {
                type empty;
                augex:data-path "clockstats";
              }
              leaf rawstats {
                type empty;
                augex:data-path "rawstats";
              }
            }
          }
        }
        container filegen {
          augex:data-path "filegen";
          augex:value-yang-path "word";
          presence "Config entry.";
          leaf word {
            mandatory true;
            type string {
              pattern "[^,# \n\t]+";
            }
          }
          list filegen-opts {
            key "_id";
            ordered-by user;
            leaf _id {
              type uint64;
              description
                "Implicitly generated list key to maintain the order of the augeas data.";
            }
            choice ch-filegen-opts {
              mandatory true;
              leaf file {
                type string {
                  pattern "[^,# \n\t]+";
                }
                augex:data-path "file";
              }
              leaf type {
                type string {
                  pattern "[^,# \n\t]+";
                }
                augex:data-path "type";
              }
              leaf enable {
                type string {
                  pattern "(en|dis)able";
                }
                augex:data-path "enable";
              }
              leaf link {
                type string {
                  pattern "(no)?link";
                }
                augex:data-path "link";
              }
            }
          }
        }
        container broadcastclient {
          augex:data-path "broadcastclient";
          presence "Config entry.";
          leaf novolley {
            type empty;
            augex:data-path "novolley";
          }
        }
        leaf controlkey {
          type string {
            pattern "[^,# \n\t]+";
          }
          augex:data-path "controlkey";
        }
        leaf keys {
          type string {
            pattern "[^,# \n\t]+";
          }
          augex:data-path "keys";
        }
        leaf keysdir {
          type string {
            pattern "[^,# \n\t]+";
          }
          augex:data-path "keysdir";
        }
        leaf requestkey {
          type string {
            pattern "[^,# \n\t]+";
          }
          augex:data-path "requestkey";
        }
        leaf authenticate {
          type string {
            pattern "[^,# \n\t]+";
          }
          augex:data-path "authenticate";
        }
        leaf autokey {
          type empty;
          augex:data-path "autokey";
        }
        leaf revoke {
          type empty;
          augex:data-path "revoke";
        }
        container trustedkey {
          augex:data-path "trustedkey";
          presence "Config entry.";
          list key-list {
            key "_id";
            min-elements 1;
            ordered-by user;
            leaf _id {
              type uint64;
              description
                "Implicitly generated list key to maintain the order of the augeas data.";
            }
            leaf key {
              mandatory true;
              type string {
                pattern "[^,# \n\t]+";
              }
              augex:data-path "key";
            }
          }
        }
        container tinker {
          augex:data-path "tinker";
          presence "Config entry.";
          list config-entries {
            key "_id";
            ordered-by user;
            leaf _id {
              type uint64;
              description
                "Implicitly generated list key to maintain the order of the augeas data.";
            }
            choice ch-config-entries {
              mandatory true;
              leaf step {
                type string {
                  pattern "[0-9]+([.,][0-9]+)?";
                }
                augex:data-path "step";
              }
              leaf panic {
                type string {
                  pattern "[0-9]+([.,][0-9]+)?";
                }
                augex:data-path "panic";
              }
              leaf dispersion {
                type string {
                  pattern "[0-9]+([.,][0-9]+)?";
                }
                augex:data-path "dispersion";
              }
              leaf stepout {
                type string {
                  pattern "[0-9]+([.,][0-9]+)?";
                }
                augex:data-path "stepout";
              }
              leaf minpoll {
                type string {
                  pattern "[0-9]+([.,][0-9]+)?";
                }
                augex:data-path "minpoll";
              }
              leaf allan {
                type string {
                  pattern "[0-9]+([.,][0-9]+)?";
                }
                augex:data-path "allan";
              }
              leaf huffpuff {
                type string {
                  pattern "[0-9]+([.,][0-9]+)?";
                }
                augex:data-path "huffpuff";
              }
            }
          }
        }
        container tos {
          augex:data-path "tos";
          presence "Config entry.";
          list config-entries {
            key "_id";
            ordered-by user;
            leaf _id {
              type uint64;
              description
                "Implicitly generated list key to maintain the order of the augeas data.";
            }
            choice ch-config-entries {
              mandatory true;
              leaf beacon {
                type string {
                  pattern "[0-9]+([.,][0-9]+)?";
                }
                augex:data-path "beacon";
              }
              leaf ceiling {
                type string {
                  pattern "[0-9]+([.,][0-9]+)?";
                }
                augex:data-path "ceiling";
              }
              leaf cohort {
                type string {
                  pattern "[0-9]+([.,][0-9]+)?";
                }
                augex:data-path "cohort";
              }
              leaf floor {
                type string {
                  pattern "[0-9]+([.,][0-9]+)?";
                }
                augex:data-path "floor";
              }
              leaf maxclock {
                type string {
                  pattern "[0-9]+([.,][0-9]+)?";
                }
                augex:data-path "maxclock";
              }
              leaf maxdist {
                type string {
                  pattern "[0-9]+([.,][0-9]+)?";
                }
                augex:data-path "maxdist";
              }
              leaf minclock {
                type string {
                  pattern "[0-9]+([.,][0-9]+)?";
                }
                augex:data-path "minclock";
              }
              leaf mindist {
                type string {
                  pattern "[0-9]+([.,][0-9]+)?";
                }
                augex:data-path "mindist";
              }
              leaf minsane {
                type string {
                  pattern "[0-9]+([.,][0-9]+)?";
                }
                augex:data-path "minsane";
              }
              leaf orphan {
                type string {
                  pattern "[0-9]+([.,][0-9]+)?";
                }
                augex:data-path "orphan";
              }
              leaf orphanwait {
                type string {
                  pattern "[0-9]+([.,][0-9]+)?";
                }
                augex:data-path "orphanwait";
              }
            }
          }
        }
        container interface {
          augex:data-path "interface";
          presence "Config entry.";
          leaf action {
            mandatory true;
            type string {
              pattern "listen|ignore|drop";
            }
            augex:data-path "action";
          }
          leaf addresses {
            mandatory true;
            type string {
              pattern "[A-Za-z0-9_.-]+";
            }
            augex:data-path "addresses";
          }
        }
      }
    }
  }
}
