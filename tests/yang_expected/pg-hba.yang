module pg-hba {
  yang-version 1.1;
  namespace "aug:pg-hba";
  prefix aug;

  import augeas-extension {
    prefix augex;
  }

  augex:augeas-mod-name "Pg_Hba";

  grouping database-list {
    list database-list {
      key "_id";
      min-elements 1;
      ordered-by user;
      leaf _id {
        type uint64;
        description
          "Implicitly generated list key to maintain the order of the augeas data.";
      }
      leaf database {
        mandatory true;
        type string {
          pattern "[^,# \n\t]+";
        }
        augex:data-path "database";
      }
    }
  }
  grouping user-list {
    list user-list {
      key "_id";
      min-elements 1;
      ordered-by user;
      leaf _id {
        type uint64;
        description
          "Implicitly generated list key to maintain the order of the augeas data.";
      }
      leaf user {
        mandatory true;
        type string {
          pattern "[^,# \n\t]+";
        }
        augex:data-path "user";
      }
    }
  }
  grouping option-list {
    list option-list {
      key "_id";
      ordered-by user;
      leaf _id {
        type uint64;
        description
          "Implicitly generated list key to maintain the order of the augeas data.";
      }
      container option {
        augex:data-path "option";
        augex:value-yang-path "word";
        presence "Config entry.";
        leaf word {
          mandatory true;
          type string {
            pattern "[A-Za-z0-9_.-]+";
          }
        }
        leaf value {
          type union {
            type string {
              pattern "[^\"' \t\n]+";
            }
            type string {
              pattern "[^\"'\n]*[ \t]+[^\"'\n]*";
            }
          }
          augex:data-path "value";
        }
      }
    }
  }
  list pg-hba {
    key "config-file";
    leaf config-file {
      type string;
    }
    list entries-list {
      key "_seq";
      ordered-by user;
      augex:data-path "$$";
      leaf _seq {
        type uint64;
        description
          "Key contains some unique value. The order is based on the actual order of list instances.";
      }
      leaf type {
        mandatory true;
        type union {
          type string {
            pattern "local";
          }
          type string {
            pattern "((host)|(hostssl))|(hostnossl)";
          }
        }
        augex:data-path "type";
      }
      choice ch-entries-list {
        mandatory true;
        container case {
          presence "Config entry.";
          when "../type='local'";
          uses database-list;
          uses user-list;
          container method {
            augex:data-path "method";
            augex:value-yang-path "value";
            presence "Config entry.";
            leaf value {
              mandatory true;
              type string {
                pattern "[A-Za-z][A-Za-z0-9-]+";
              }
            }
            uses option-list;
          }
        }
        container case2 {
          presence "Config entry.";
          when "re-match(../type, '((host)|(hostssl))|(hostnossl)')";
          uses database-list;
          uses user-list;
          leaf address {
            mandatory true;
            type string {
              pattern "([0-9a-fA-F:.]+(/[0-9]+|[ \t]+[0-9.]+))|(\\.?[a-zA-Z0-9]([a-zA-Z0-9-]*[a-zA-Z0-9])?(\\.[a-zA-Z0-9]([a-zA-Z0-9-]*[a-zA-Z0-9])?)*)";
            }
            augex:data-path "address";
          }
          container method {
            augex:data-path "method";
            augex:value-yang-path "value";
            presence "Config entry.";
            leaf value {
              mandatory true;
              type string {
                pattern "[A-Za-z][A-Za-z0-9-]+";
              }
            }
            uses option-list;
          }
        }
      }
    }
  }
}
