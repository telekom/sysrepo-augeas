module xymon {
  yang-version 1.1;
  namespace "aug:xymon";
  prefix aug;

  import augeas-extension {
    prefix augex;
  }
  import ietf-inet-types {
    prefix inet;
    reference
      "RFC 6991: Common YANG Data Types";
  }

  augex:augeas-mod-name "Xymon";

  grouping host {
    leaf ip {
      mandatory true;
      type inet:ip-address-no-zone;
      augex:data-path "ip";
    }
    leaf fqdn {
      mandatory true;
      type string {
        pattern "[A-Za-z0-9_.-]+";
      }
      augex:data-path "fqdn";
    }
    list tag-list {
      key "_id";
      ordered-by user;
      leaf _id {
        type uint64;
        description
          "Implicitly generated list key to maintain the order of the augeas data.";
      }
      leaf tag {
        mandatory true;
        type string {
          pattern "[^ \n\t]+";
        }
        augex:data-path "tag";
      }
    }
  }
  grouping group {
    list config-entries {
      key "_id";
      ordered-by user;
      leaf _id {
        type uint64;
        description
          "Implicitly generated list key to maintain the order of the augeas data.";
      }
      choice ch-config-entries {
        mandatory true;
        container host {
          augex:data-path "host";
          presence "Config entry.";
          uses host;
        }
        leaf title {
          type string {
            pattern "[^ \t][^\n]+";
          }
          augex:data-path "title";
        }
      }
    }
  }
  grouping page {
    list config-entries {
      key "_id";
      ordered-by user;
      leaf _id {
        type uint64;
        description
          "Implicitly generated list key to maintain the order of the augeas data.";
      }
      choice ch-config-entries {
        mandatory true;
        leaf title {
          type string {
            pattern "[^ \t][^\n]+";
          }
          augex:data-path "title";
        }
        leaf include {
          type string {
            pattern "[^ \t][^\n]+";
          }
          augex:data-path "include";
        }
        leaf dispinclude {
          type string {
            pattern "[^ \t][^\n]+";
          }
          augex:data-path "dispinclude";
        }
        leaf netinclude {
          type string {
            pattern "[^ \t][^\n]+";
          }
          augex:data-path "netinclude";
        }
        leaf directory {
          type string {
            pattern "[^ \t][^\n]+";
          }
          augex:data-path "directory";
        }
        container host {
          augex:data-path "host";
          presence "Config entry.";
          uses host;
        }
      }
    }
  }
  grouping ch-group {
    choice ch-group {
      mandatory true;
      container group {
        augex:data-path "group";
        augex:value-yang-path "value-to-eol";
        presence "Config entry.";
        leaf value-to-eol {
          mandatory true;
          type string {
            pattern "[^ \t][^\n]+";
          }
        }
        uses group;
      }
      container group-compress {
        augex:data-path "group-compress";
        augex:value-yang-path "value-to-eol";
        presence "Config entry.";
        leaf value-to-eol {
          mandatory true;
          type string {
            pattern "[^ \t][^\n]+";
          }
        }
        uses group;
      }
      container group-sorted {
        augex:data-path "group-sorted";
        augex:value-yang-path "value-to-eol";
        presence "Config entry.";
        leaf value-to-eol {
          mandatory true;
          type string {
            pattern "[^ \t][^\n]+";
          }
        }
        uses group;
      }
      container group-only {
        augex:data-path "group-only";
        augex:value-yang-path "value-to-eol";
        presence "Config entry.";
        list group-only-col-list {
          key "_id";
          min-elements 1;
          ordered-by user;
          leaf _id {
            type uint64;
            description
              "Implicitly generated list key to maintain the order of the augeas data.";
          }
          leaf col {
            mandatory true;
            type string {
              pattern "[A-Za-z0-9_.-]+";
            }
            augex:data-path "col";
          }
        }
        leaf value-to-eol {
          mandatory true;
          type string {
            pattern "[^ \t][^\n]+";
          }
        }
        uses group;
      }
    }
  }
  grouping page2 {
    leaf pagetitle {
      type string {
        pattern "[^ \t][^\n]+";
      }
      augex:data-path "pagetitle";
    }
    uses page;
    list ch-group-list {
      key "_id";
      ordered-by user;
      leaf _id {
        type uint64;
        description
          "Implicitly generated list key to maintain the order of the augeas data.";
      }
      uses ch-group;
    }
  }
  list xymon {
    key "config-file";
    leaf config-file {
      type string;
    }
    list config-entries {
      key "_id";
      ordered-by user;
      leaf _id {
        type uint64;
        description
          "Implicitly generated list key to maintain the order of the augeas data.";
      }
      choice ch-config-entries {
        mandatory true;
        leaf include {
          type string {
            pattern "[^ \t][^\n]+";
          }
          augex:data-path "include";
        }
        leaf dispinclude {
          type string {
            pattern "[^ \t][^\n]+";
          }
          augex:data-path "dispinclude";
        }
        leaf netinclude {
          type string {
            pattern "[^ \t][^\n]+";
          }
          augex:data-path "netinclude";
        }
        leaf directory {
          type string {
            pattern "[^ \t][^\n]+";
          }
          augex:data-path "directory";
        }
        container host {
          augex:data-path "host";
          presence "Config entry.";
          uses host;
        }
        leaf title {
          type string {
            pattern "[^ \t][^\n]+";
          }
          augex:data-path "title";
        }
        container ospage {
          augex:data-path "ospage";
          augex:value-yang-path "word";
          presence "Config entry.";
          leaf word {
            mandatory true;
            type string {
              pattern "[A-Za-z0-9_.-]+";
            }
          }
          leaf ospagetitle {
            mandatory true;
            type string {
              pattern "[^ \t][^\n]+";
            }
            augex:data-path "ospagetitle";
          }
        }
      }
    }
    list ch-group-list {
      key "_id";
      ordered-by user;
      leaf _id {
        type uint64;
        description
          "Implicitly generated list key to maintain the order of the augeas data.";
      }
      uses ch-group;
    }
    list config-entries2 {
      key "_id";
      ordered-by user;
      leaf _id {
        type uint64;
        description
          "Implicitly generated list key to maintain the order of the augeas data.";
      }
      choice ch-config-entries2 {
        mandatory true;
        container page {
          augex:data-path "page";
          augex:value-yang-path "page-name";
          presence "Config entry.";
          leaf page-name {
            mandatory true;
            type string {
              pattern "[A-Za-z0-9_.-]+";
            }
          }
          uses page2;
        }
        container subpage {
          augex:data-path "subpage";
          augex:value-yang-path "page-name";
          presence "Config entry.";
          leaf page-name {
            mandatory true;
            type string {
              pattern "[A-Za-z0-9_.-]+";
            }
          }
          uses page2;
        }
        container subparent {
          augex:data-path "subparent";
          augex:value-yang-path "page-name";
          presence "Config entry.";
          leaf parent {
            mandatory true;
            type string {
              pattern "[A-Za-z0-9_.-]+";
            }
            augex:data-path "parent";
          }
          leaf page-name {
            mandatory true;
            type string {
              pattern "[A-Za-z0-9_.-]+";
            }
          }
          leaf pagetitle {
            type string {
              pattern "[^ \t][^\n]+";
            }
            augex:data-path "pagetitle";
          }
          uses page;
          list ch-group-list {
            key "_id";
            ordered-by user;
            leaf _id {
              type uint64;
              description
                "Implicitly generated list key to maintain the order of the augeas data.";
            }
            uses ch-group;
          }
        }
      }
    }
  }
}
