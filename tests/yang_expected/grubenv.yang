module grubenv {
  yang-version 1.1;
  namespace "aug:grubenv";
  prefix aug;

  import augeas-extension {
    prefix augex;
  }

  augex:augeas-mod-name "GrubEnv";

  list grubenv {
    key "config-file";
    leaf config-file {
      type string;
    }
    list target-list {
      key "_seq";
      ordered-by user;
      augex:data-path "$$";
      leaf _seq {
        type uint64;
        description
          "Key contains some unique value. The order is based on the actual order of list instances.";
      }
      leaf name {
        mandatory true;
        type string {
          pattern "[A-Za-z_][A-Za-z0-9_]*";
        }
        augex:data-path "name";
      }
      leaf value {
        mandatory true;
        type string {
          pattern "[^\\\\\n]*(\\\\(\\\\|\n)[^\\\\\n]*)*";
        }
        augex:data-path "value";
      }
    }
  }
}
