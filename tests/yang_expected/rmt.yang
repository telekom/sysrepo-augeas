module rmt {
  yang-version 1.1;
  namespace "aug:rmt";
  prefix aug;

  import augeas-extension {
    prefix augex;
  }

  augex:augeas-mod-name "Rmt";

  list rmt {
    key "config-file";
    leaf config-file {
      type string;
    }
    list config-entries {
      key "_id";
      ordered-by user;
      leaf _id {
        type uint64;
        description
          "Implicitly generated list key to maintain the order of the augeas data.";
      }
      choice ch-config-entries {
        mandatory true;
        leaf debug {
          type string {
            pattern "[^ \t\n]+";
          }
          augex:data-path "DEBUG";
        }
        leaf user {
          type string {
            pattern "[^ \t\n]+";
          }
          augex:data-path "USER";
        }
        container access {
          augex:data-path "ACCESS";
          presence "Config entry.";
          leaf name {
            mandatory true;
            type string {
              pattern "[^ \t\n]+";
            }
            augex:data-path "name";
          }
          leaf host {
            mandatory true;
            type string {
              pattern "[^ \t\n]+";
            }
            augex:data-path "host";
          }
          leaf path {
            mandatory true;
            type string {
              pattern "[^ \t\n]+";
            }
            augex:data-path "path";
          }
        }
      }
    }
  }
}
