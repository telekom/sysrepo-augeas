module pylonspaste {
  yang-version 1.1;
  namespace "aug:pylonspaste";
  prefix aug;

  import augeas-extension {
    prefix augex;
  }

  augex:augeas-mod-name "Pylonspaste";

  list pylonspaste {
    key "config-file";
    leaf config-file {
      type string;
    }
    list record-list {
      key "_id";
      ordered-by user;
      leaf _id {
        type uint64;
        description
          "Implicitly generated list key to maintain the order of the augeas data.";
      }
      container record {
        augex:data-path "$$";
        presence "Config entry.";
        leaf record {
          mandatory true;
          type string {
            pattern "#commen((t[^\\]\n/]|[^\\]\n/t])[^\\]\n/]*|())|#comme([^\\]\n/n][^\\]\n/]*|())|#comm([^\\]\n/e][^\\]\n/]*|())|#com([^\\]\n/m][^\\]\n/]*|())|#co([^\\]\n/m][^\\]\n/]*|())|#c([^\\]\n/o][^\\]\n/]*|())|(#[^\\]\n/c]|[^\\]\n#/][^\\]\n/])[^\\]\n/]*|#|[^\\]\n#/]";
          }
        }
        list config-entries {
          key "_id";
          ordered-by user;
          leaf _id {
            type uint64;
            description
              "Implicitly generated list key to maintain the order of the augeas data.";
          }
          choice ch-config-entries {
            mandatory true;
            leaf debug {
              type string {
                pattern "[^ \t\n].*[^ \t\n]|[^ \t\n]";
              }
              augex:data-path "debug";
            }
            container plugins {
              augex:data-path "plugins";
              presence "Config entry.";
              list items-list {
                key "_seq";
                ordered-by user;
                augex:data-path "$$";
                augex:value-yang-path "plugin";
                leaf _seq {
                  type uint64;
                  description
                    "Key contains some unique value. The order is based on the actual order of list instances.";
                }
                leaf plugin {
                  mandatory true;
                  type string {
                    pattern "[A-Za-z][;:#A-Za-z0-9._-]+";
                  }
                }
              }
            }
            container normal-opts {
              augex:data-path "$$";
              augex:value-yang-path "space-in";
              presence "Config entry.";
              leaf normal-opts {
                mandatory true;
                type string {
                  pattern "debu((g[#.0-:A-Z_a-z-]|[#.0-:A-Z_a-fh-z-])[#.0-:A-Z_a-z-]*|())|deb([#.0-:A-Z_a-tv-z-][#.0-:A-Z_a-z-]*|())|de([#.0-:A-Z_ac-z-][#.0-:A-Z_a-z-]*|())|plugin((s[#.0-:A-Z_a-z-]|[#.0-:A-Z_a-rt-z-])[#.0-:A-Z_a-z-]*|())|plugi([#.0-:A-Z_a-mo-z-][#.0-:A-Z_a-z-]*|())|plug([#.0-:A-Z_a-hj-z-][#.0-:A-Z_a-z-]*|())|plu([#.0-:A-Z_a-fh-z-][#.0-:A-Z_a-z-]*|())|(pl[#.0-:A-Z_a-tv-z-]|(p[#.0-:A-Z_a-km-z-]|d[#.0-:A-Z_a-df-z-]|[A-Za-ce-oq-z][#.0-:A-Z_a-z-])[#.0-:A-Z_a-z-])[#.0-:A-Z_a-z-]*|pl|p[#.0-:A-Z_a-km-z-]|d[#.0-:A-Z_a-df-z-]|[A-Za-ce-oq-z][#.0-:A-Z_a-z-]";
                }
              }
              leaf space-in {
                type string {
                  pattern "[^ \t\n].*[^ \t\n]|[^ \t\n]";
                }
              }
            }
          }
        }
      }
    }
  }
}
