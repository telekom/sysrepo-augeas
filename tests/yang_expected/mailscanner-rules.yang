module mailscanner-rules {
  yang-version 1.1;
  namespace "aug:mailscanner-rules";
  prefix aug;

  import augeas-extension {
    prefix augex;
  }

  augex:augeas-mod-name "Mailscanner_Rules";

  list mailscanner-rules {
    key "config-file";
    leaf config-file {
      type string;
    }
    list rule-list {
      key "_seq";
      ordered-by user;
      augex:data-path "$$";
      leaf _seq {
        type uint64;
        description
          "Key contains some unique value. The order is based on the actual order of list instances.";
      }
      leaf action {
        mandatory true;
        type string {
          pattern "allow|deny|deny\\+delete|rename|rename[ ]+to[ ]+[^# \t\n]+|([A-Za-z0-9_+.-]+@[A-Za-z0-9_.-]+[, ]?)+";
        }
        augex:data-path "action";
      }
      leaf regex {
        mandatory true;
        type string {
          pattern "[^\t\n]+";
        }
        augex:data-path "regex";
      }
      leaf log-text {
        mandatory true;
        type string {
          pattern "[^\t\n]+";
        }
        augex:data-path "log-text";
      }
      leaf user-report {
        mandatory true;
        type string {
          pattern "[^\t\n]+";
        }
        augex:data-path "user-report";
      }
    }
  }
}
