module cachefilesd {
  yang-version 1.1;
  namespace "aug:cachefilesd";
  prefix aug;

  import augeas-extension {
    prefix augex;
  }

  augex:augeas-mod-name "Cachefilesd";

  list cachefilesd {
    key "config-file";
    leaf config-file {
      type string;
    }
    list config-entries {
      key "_id";
      ordered-by user;
      leaf _id {
        type uint64;
        description
          "Implicitly generated list key to maintain the order of the augeas data.";
      }
      choice ch-config-entries {
        mandatory true;
        container cacheconfig {
          augex:data-path "$$";
          augex:value-yang-path "entry-value";
          presence "Config entry.";
          leaf label {
            mandatory true;
            type string {
              pattern "[A-Za-z0-9_.-]+";
              pattern "(?i)nocull" {
                modifier invert-match;
              }
            }
          }
          leaf entry-value {
            mandatory true;
            type string {
              pattern "[A-Za-z0-9_.-:%]+";
            }
          }
        }
        leaf nocull {
          type string {
            pattern "(?i)nocull";
          }
          augex:data-path "$$";
        }
      }
    }
  }
}
