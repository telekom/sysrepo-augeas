module postfix_sasl_smtpd {
  namespace "aug:postfix_sasl_smtpd";
  prefix aug;

  import augeas-extension {
    prefix augex;
  }

  augex:augeas-mod-name "Postfix_sasl_smtpd";

  list postfix_sasl_smtpd {
    key "config-file";
    leaf config-file {
      type string;
    }
    list config-entries {
      key "_id";
      min-elements 1;
      ordered-by user;
      leaf _id {
        type uint64;
        description
          "Implicitly generated list key to maintain the order of the augeas data.";
      }
      choice ch_config-entries {
        mandatory true;
        leaf pwcheck_method {
          type string {
            pattern "[^ \t\n].*[^ \t\n]|[^ \t\n]";
          }
          augex:data-path "pwcheck_method";
        }
        leaf auxprop_plugin {
          type string {
            pattern "[^ \t\n].*[^ \t\n]|[^ \t\n]";
          }
          augex:data-path "auxprop_plugin";
        }
        leaf saslauthd_path {
          type string {
            pattern "[^ \t\n].*[^ \t\n]|[^ \t\n]";
          }
          augex:data-path "saslauthd_path";
        }
        leaf mech_list {
          type string {
            pattern "[^ \t\n].*[^ \t\n]|[^ \t\n]";
          }
          augex:data-path "mech_list";
        }
        leaf sql_engine {
          type string {
            pattern "[^ \t\n].*[^ \t\n]|[^ \t\n]";
          }
          augex:data-path "sql_engine";
        }
        leaf log_level {
          type string {
            pattern "[^ \t\n].*[^ \t\n]|[^ \t\n]";
          }
          augex:data-path "log_level";
        }
        leaf auto_transition {
          type string {
            pattern "[^ \t\n].*[^ \t\n]|[^ \t\n]";
          }
          augex:data-path "auto_transition";
        }
      }
    }
  }
}
