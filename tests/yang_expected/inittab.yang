module inittab {
  yang-version 1.1;
  namespace "aug:inittab";
  prefix aug;

  import augeas-extension {
    prefix augex;
  }

  augex:augeas-mod-name "Inittab";

  list inittab {
    key "config-file";
    leaf config-file {
      type string;
    }
    list record-list {
      key "_id";
      ordered-by user;
      leaf _id {
        type uint64;
        description
          "Implicitly generated list key to maintain the order of the augeas data.";
      }
      container record {
        augex:data-path "$$";
        presence "Config entry.";
        leaf id {
          mandatory true;
          type string {
            pattern "[^/#:\n]{1,4}";
          }
        }
        leaf runlevels {
          mandatory true;
          type string {
            pattern "[^#:\n]*";
          }
          augex:data-path "runlevels";
        }
        leaf action {
          mandatory true;
          type string {
            pattern "[^#:\n]*";
          }
          augex:data-path "action";
        }
        leaf process {
          mandatory true;
          type string {
            pattern "[^#\n]*";
          }
          augex:data-path "process";
        }
      }
    }
  }
}
