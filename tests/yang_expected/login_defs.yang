module login_defs {
  namespace "aug:login_defs";
  prefix aug;

  import augeas-extension {
    prefix augex;
  }

  augex:augeas-mod-name "Login_defs";

  list login_defs {
    key "config-file";
    leaf config-file {
      type string;
    }
    list record-list {
      key "_id";
      ordered-by user;
      leaf _id {
        type uint64;
        description
          "Implicitly generated list key to maintain the order of the augeas data.";
      }
      container record {
        augex:data-path "$$";
        augex:value-yang-path "value";
        presence "Config entry.";
        leaf word {
          mandatory true;
          type string {
            pattern "[A-Za-z0-9_.-]+";
          }
        }
        leaf value {
          mandatory true;
          type string {
            pattern "[^ \t\n]+([ \t]+[^ \t\n]+)*";
          }
        }
      }
    }
  }
}
