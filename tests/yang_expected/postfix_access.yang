module postfix_access {
  namespace "aug:postfix_access";
  prefix aug;

  import augeas-extension {
    prefix augex;
  }

  augex:augeas-mod-name "Postfix_Access";

  list postfix_access {
    key "config-file";
    leaf config-file {
      type string;
    }
    list record-list {
      key "_id";
      ordered-by user;
      leaf _id {
        type uint64;
        description
          "Implicitly generated list key to maintain the order of the augeas data.";
      }
      container record {
        augex:data-path "$$";
        presence "Config entry.";
        leaf spec {
          mandatory true;
          type uint64;
        }
        leaf pattern {
          mandatory true;
          type string {
            pattern "([^# \n\t])+";
          }
          augex:data-path "pattern";
        }
        leaf action {
          mandatory true;
          type string {
            pattern "([^# \n\t])+";
          }
          augex:data-path "action";
        }
        leaf parameters {
          type string {
            pattern "([^# \n\t])|((([^# \n\t])((([^#\n])|(\n[ \t]+))*))([^# \n\t]))";
          }
          augex:data-path "parameters";
        }
      }
    }
  }
}
