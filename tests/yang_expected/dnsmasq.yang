module dnsmasq {
  yang-version 1.1;
  namespace "aug:dnsmasq";
  prefix aug;

  import augeas-extension {
    prefix augex;
  }

  augex:augeas-mod-name "Dnsmasq";

  list dnsmasq {
    key "config-file";
    leaf config-file {
      type string;
    }
    list config-entries {
      key "_id";
      ordered-by user;
      leaf _id {
        type uint64;
        description
          "Implicitly generated list key to maintain the order of the augeas data.";
      }
      choice ch-config-entries {
        mandatory true;
        container address {
          augex:data-path "address";
          augex:value-yang-path "sto-no-slash";
          presence "Config entry.";
          list domain-list {
            key "_id";
            min-elements 1;
            ordered-by user;
            leaf _id {
              type uint64;
              description
                "Implicitly generated list key to maintain the order of the augeas data.";
            }
            leaf domain {
              mandatory true;
              type string {
                pattern "[^/ \t\n]+";
              }
              augex:data-path "domain";
            }
          }
          leaf sto-no-slash {
            mandatory true;
            type string {
              pattern "[^/ \t\n]+";
            }
          }
        }
        container server {
          augex:data-path "server";
          augex:value-yang-path "value";
          presence "Config entry.";
          list domain-list {
            key "_id";
            ordered-by user;
            leaf _id {
              type uint64;
              description
                "Implicitly generated list key to maintain the order of the augeas data.";
            }
            leaf domain {
              mandatory true;
              type string {
                pattern "[^/ \t\n]+";
              }
              augex:data-path "domain";
            }
          }
          leaf value {
            type string {
              pattern "#|([^#@/ \t\n]+)";
            }
          }
          leaf port {
            type uint64;
            augex:data-path "port";
          }
          container source {
            augex:data-path "source";
            augex:value-yang-path "value";
            presence "Config entry.";
            leaf value {
              mandatory true;
              type string {
                pattern "[^#/ \t\n]+";
              }
            }
            leaf port {
              type uint64;
              augex:data-path "port";
            }
          }
        }
        container entry {
          augex:data-path "$$";
          augex:value-yang-path "sto-to-eol";
          presence "Config entry.";
          leaf entry {
            mandatory true;
            type string {
              pattern "[A-Za-z0-9_.-]+";
              pattern "address|server" {
                modifier invert-match;
              }
            }
          }
          leaf sto-to-eol {
            type string {
              pattern "[^ \t\n].*[^ \t\n]|[^ \t\n]";
            }
          }
        }
      }
    }
  }
}
