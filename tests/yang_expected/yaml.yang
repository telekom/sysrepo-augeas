module yaml {
  yang-version 1.1;
  namespace "aug:yaml";
  prefix aug;

  import augeas-extension {
    prefix augex;
  }

  augex:augeas-mod-name "YAML";

  grouping repo {
    container repo {
      augex:data-path "$$";
      augex:value-yang-path "val";
      presence "Config entry.";
      leaf word {
        mandatory true;
        type string {
          pattern "[A-Za-z0-9_.-]+";
        }
      }
      choice ch-repo {
        mandatory true;
        leaf val {
          type string {
            pattern "[A-Za-z0-9_.-]+";
          }
        }
        container mval {
          augex:data-path "@mval";
          presence "Config entry.";
          list line-list {
            key "_id";
            min-elements 1;
            ordered-by user;
            leaf _id {
              type uint64;
              description
                "Implicitly generated list key to maintain the order of the augeas data.";
            }
            leaf line {
              mandatory true;
              type string {
                pattern "[^ \t\n].*[^ \t\n]|[^ \t\n]";
              }
              augex:data-path "@line";
            }
          }
        }
      }
    }
  }
  grouping repo-list {
    list repo-list {
      key "_id";
      min-elements 1;
      ordered-by user;
      leaf _id {
        type uint64;
        description
          "Implicitly generated list key to maintain the order of the augeas data.";
      }
      uses repo;
    }
  }
  list yaml {
    key "config-file";
    leaf config-file {
      type string;
    }
    leaf yaml {
      type union {
        type empty;
        type string {
          pattern "[^ \t\n].*[^ \t\n]|[^ \t\n]";
        }
      }
      augex:data-path "@yaml";
    }
    list config-entries {
      key "_id";
      ordered-by user;
      leaf _id {
        type uint64;
        description
          "Implicitly generated list key to maintain the order of the augeas data.";
      }
      choice ch-config-entries {
        mandatory true;
        container sequence {
          augex:data-path "@sequence";
          presence "Config entry.";
          uses repo-list;
        }
        container entry {
          augex:data-path "$$";
          augex:value-yang-path "val";
          presence "Config entry.";
          leaf word {
            mandatory true;
            type string {
              pattern "[A-Za-z0-9_.-]+";
            }
          }
          leaf val {
            type string {
              pattern "[A-Za-z0-9_.-]+";
            }
          }
          choice ch-entry {
            mandatory true;
            container case {
              presence "Config entry.";
              container inherit {
                augex:data-path "$$";
                augex:value-yang-path "val";
                presence "Config entry.";
                leaf label {
                  mandatory true;
                  type string {
                    pattern "<<";
                  }
                }
                leaf val {
                  mandatory true;
                  type string {
                    pattern "[A-Za-z0-9_.-]+";
                  }
                }
              }
              list repo-list {
                key "_id";
                ordered-by user;
                leaf _id {
                  type uint64;
                  description
                    "Implicitly generated list key to maintain the order of the augeas data.";
                }
                uses repo;
              }
            }
            container case2 {
              presence "Config entry.";
              uses repo-list;
            }
          }
        }
      }
    }
  }
}
