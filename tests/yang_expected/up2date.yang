module up2date {
  yang-version 1.1;
  namespace "aug:up2date";
  prefix aug;

  import augeas-extension {
    prefix augex;
  }

  augex:augeas-mod-name "Up2date";

  list up2date {
    key "config-file";
    leaf config-file {
      type string;
    }
    list entry-list {
      key "_seq";
      ordered-by user;
      augex:data-path "$$";
      augex:value-yang-path "key";
      leaf _seq {
        type uint64;
        description
          "Key contains some unique value. The order is based on the actual order of list instances.";
      }
      leaf key {
        mandatory true;
        type string {
          pattern "[^=# \t\n]+";
        }
      }
      choice ch-entry-list {
        container values {
          augex:data-path "values";
          presence "Config entry.";
          list multi-list {
            key "_seq";
            ordered-by user;
            augex:data-path "$$";
            augex:value-yang-path "value";
            leaf _seq {
              type uint64;
              description
                "Key contains some unique value. The order is based on the actual order of list instances.";
            }
            leaf value {
              type string {
                pattern "[^ \t\n;][^\n;]*[^ \t\n;]|[^ \t\n;]";
              }
            }
          }
        }
        leaf value {
          type string {
            pattern "[^ \t\n;][^\n;]*[^ \t\n;]|[^ \t\n;]";
          }
          augex:data-path "value";
        }
      }
    }
  }
}
