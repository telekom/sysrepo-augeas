module inputrc {
  yang-version 1.1;
  namespace "aug:inputrc";
  prefix aug;

  import augeas-extension {
    prefix augex;
  }

  augex:augeas-mod-name "Inputrc";

  grouping variable {
    container variable {
      augex:data-path "$$";
      augex:value-yang-path "word";
      presence "Config entry.";
      leaf label {
        mandatory true;
        type string {
          pattern "[A-Za-z0-9_.-]+";
          pattern "entry" {
            modifier invert-match;
          }
        }
      }
      leaf word {
        mandatory true;
        type string {
          pattern "[A-Za-z0-9_.-]+";
        }
      }
    }
  }
  list inputrc {
    key "config-file";
    leaf config-file {
      type string;
    }
    list config-entries {
      key "_id";
      ordered-by user;
      leaf _id {
        type uint64;
        description
          "Implicitly generated list key to maintain the order of the augeas data.";
      }
      choice ch-config-entries {
        mandatory true;
        list if-list {
          key "_r-id";
          leaf _r-id {
            type uint64;
            description
              "Implicitly generated list key to maintain the recursive augeas data.";
          }
          container if {
            augex:data-path "@if";
            augex:value-yang-path "space-in";
            presence "Config entry.";
            leaf space-in {
              mandatory true;
              type string {
                pattern "[^ \t\n].*[^ \t\n]|[^ \t\n]";
              }
            }
            list config-entries {
              key "_id";
              ordered-by user;
              leaf _id {
                type uint64;
                description
                  "Implicitly generated list key to maintain the order of the augeas data.";
              }
              choice ch-config-entries {
                mandatory true;
                leaf _if-ref {
                  type leafref {
                    path "../../../../if-list/_r-id";
                  }
                  description
                    "Implicitly generated leaf to maintain recursive augeas data.";
                }
                leaf include {
                  type string {
                    pattern "[^ \t\n].*[^ \t\n]|[^ \t\n]";
                  }
                  augex:data-path "@include";
                }
                case variable {
                  uses variable;
                }
                container entry {
                  augex:data-path "entry";
                  augex:value-yang-path "value";
                  presence "Config entry.";
                  leaf value {
                    mandatory true;
                    type string {
                      pattern "[^\" \t\n]+";
                    }
                  }
                  leaf mapping {
                    mandatory true;
                    type string {
                      pattern "[A-Za-z0-9_.\"\\\\*/+\\\\,\\\\-]+";
                    }
                    augex:data-path "mapping";
                  }
                }
              }
            }
            container else {
              augex:data-path "@else";
              presence "Config entry.";
              list config-entries {
                key "_id";
                ordered-by user;
                leaf _id {
                  type uint64;
                  description
                    "Implicitly generated list key to maintain the order of the augeas data.";
                }
                choice ch-config-entries {
                  mandatory true;
                  leaf _if-ref {
                    type leafref {
                      path "../../../../../if-list/_r-id";
                    }
                    description
                      "Implicitly generated leaf to maintain recursive augeas data.";
                  }
                  leaf include {
                    type string {
                      pattern "[^ \t\n].*[^ \t\n]|[^ \t\n]";
                    }
                    augex:data-path "@include";
                  }
                  case variable {
                    uses variable;
                  }
                  container entry {
                    augex:data-path "entry";
                    augex:value-yang-path "value";
                    presence "Config entry.";
                    leaf value {
                      mandatory true;
                      type string {
                        pattern "[^\" \t\n]+";
                      }
                    }
                    leaf mapping {
                      mandatory true;
                      type string {
                        pattern "[A-Za-z0-9_.\"\\\\*/+\\\\,\\\\-]+";
                      }
                      augex:data-path "mapping";
                    }
                  }
                }
              }
            }
          }
        }
        leaf include {
          type string {
            pattern "[^ \t\n].*[^ \t\n]|[^ \t\n]";
          }
          augex:data-path "@include";
        }
        case variable {
          uses variable;
        }
        container entry {
          augex:data-path "entry";
          augex:value-yang-path "value";
          presence "Config entry.";
          leaf value {
            mandatory true;
            type string {
              pattern "[^\" \t\n]+";
            }
          }
          leaf mapping {
            mandatory true;
            type string {
              pattern "[A-Za-z0-9_.\"\\\\*/+\\\\,\\\\-]+";
            }
            augex:data-path "mapping";
          }
        }
      }
    }
  }
}
