module puppetfile {
  yang-version 1.1;
  namespace "aug:puppetfile";
  prefix aug;

  import augeas-extension {
    prefix augex;
  }

  augex:augeas-mod-name "Puppetfile";

  list puppetfile {
    key "config-file";
    leaf config-file {
      type string;
    }
    list config-entries {
      key "_id";
      ordered-by user;
      leaf _id {
        type uint64;
        description
          "Implicitly generated list key to maintain the order of the augeas data.";
      }
      choice ch-config-entries {
        mandatory true;
        leaf forge {
          type string {
            pattern "[^#\n]*";
          }
          augex:data-path "forge";
        }
        leaf metadata {
          type empty;
          augex:data-path "metadata";
        }
        container mod {
          augex:data-path "$$";
          augex:value-yang-path "value";
          presence "Config entry.";
          leaf mod {
            mandatory true;
            type uint64;
          }
          leaf value {
            mandatory true;
            type string {
              pattern "((([A-Za-z0-9_.-]+)([/-])){0,1})([A-Za-z0-9_.-]+)";
            }
          }
          leaf version {
            type string {
              pattern "[^#:\n]+";
            }
            augex:data-path "@version";
          }
          list opt-list {
            key "_id";
            ordered-by user;
            leaf _id {
              type uint64;
              description
                "Implicitly generated list key to maintain the order of the augeas data.";
            }
            container opt {
              augex:data-path "$$";
              augex:value-yang-path "value";
              presence "Config entry.";
              leaf word {
                mandatory true;
                type string {
                  pattern "[A-Za-z0-9_.-]+";
                }
              }
              leaf value {
                type string {
                  pattern "[^#\"', \t\n][^#\"',\n]*[^#\"', \t\n]|[^#\"', \t\n]";
                }
              }
            }
          }
        }
        leaf moduledir {
          type string {
            pattern "[^#\n]*";
          }
          augex:data-path "moduledir";
        }
      }
    }
  }
}
