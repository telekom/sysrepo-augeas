module limits {
  yang-version 1.1;
  namespace "aug:limits";
  prefix aug;

  import augeas-extension {
    prefix augex;
  }

  augex:augeas-mod-name "Limits";

  list limits {
    key "config-file";
    leaf config-file {
      type string;
    }
    list entry-list {
      key "_id";
      ordered-by user;
      leaf _id {
        type uint64;
        description
          "Implicitly generated list key to maintain the order of the augeas data.";
      }
      container domain {
        augex:data-path "domain";
        augex:value-yang-path "value";
        presence "Config entry.";
        leaf value {
          mandatory true;
          type string {
            pattern "[%@]?[A-Za-z0-9_.:-]+|\\*";
          }
        }
        leaf type {
          mandatory true;
          type string {
            pattern "((soft)|(hard))|(-)";
          }
          augex:data-path "type";
        }
        leaf item {
          mandatory true;
          type string {
            pattern "((((((((((((((((((core)|(data))|(fsize))|(memlock))|(nofile))|(rss))|(stack))|(cpu))|(nproc))|(as))|(maxlogins))|(maxsyslogins))|(priority))|(locks))|(sigpending))|(msgqueue))|(nice))|(rtprio))|(chroot)";
          }
          augex:data-path "item";
        }
        leaf value2 {
          mandatory true;
          type string {
            pattern "[A-Za-z0-9_./-]+";
          }
          augex:data-path "value";
        }
      }
    }
  }
}
