module iscsid {
  yang-version 1.1;
  namespace "aug:iscsid";
  prefix aug;

  import augeas-extension {
    prefix augex;
  }

  augex:augeas-mod-name "Iscsid";

  list iscsid {
    key "config-file";
    leaf config-file {
      type string;
    }
    list kv-list {
      key "_id";
      ordered-by user;
      leaf _id {
        type uint64;
        description
          "Implicitly generated list key to maintain the order of the augeas data.";
      }
      container kv {
        augex:data-path "$$";
        augex:value-yang-path "value";
        presence "Config entry.";
        leaf key {
          mandatory true;
          type string {
            pattern "[\\]\\[A-Za-z0-9_.-]+";
          }
        }
        leaf value {
          mandatory true;
          type string {
            pattern "[^ \t\n](.*[^ \t\n])?";
          }
        }
      }
    }
  }
}
