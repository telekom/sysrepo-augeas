module modules {
  yang-version 1.1;
  namespace "aug:modules";
  prefix aug;

  import augeas-extension {
    prefix augex;
  }

  augex:augeas-mod-name "Modules";

  list modules {
    key "config-file";
    leaf config-file {
      type string;
    }
    list record-list {
      key "_id";
      ordered-by user;
      leaf _id {
        type uint64;
        description
          "Implicitly generated list key to maintain the order of the augeas data.";
      }
      container record {
        augex:data-path "$$";
        augex:value-yang-path "sto-line";
        presence "Config entry.";
        leaf word {
          mandatory true;
          type string {
            pattern "[^#, \n\t/]+";
          }
        }
        leaf sto-line {
          type string {
            pattern "[^# \t\n].*[^ \t\n]|[^# \t\n]";
          }
        }
      }
    }
  }
}
