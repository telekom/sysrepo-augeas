module vmware-config {
  yang-version 1.1;
  namespace "aug:vmware-config";
  prefix aug;

  import augeas-extension {
    prefix augex;
  }

  augex:augeas-mod-name "VMware_Config";

  list vmware-config {
    key "config-file";
    leaf config-file {
      type string;
    }
    list entry-list {
      key "_id";
      ordered-by user;
      leaf _id {
        type uint64;
        description
          "Implicitly generated list key to maintain the order of the augeas data.";
      }
      container entry {
        augex:data-path "$$";
        augex:value-yang-path "double-opt";
        presence "Config entry.";
        leaf word {
          mandatory true;
          type string {
            pattern "[A-Za-z0-9_.-]+";
          }
        }
        leaf double-opt {
          mandatory true;
          type string {
            pattern "[^\n\t \"]([^\n\"]*[^\n\t \"])?";
          }
        }
      }
    }
  }
}
