module schroot {
  yang-version 1.1;
  namespace "aug:schroot";
  prefix aug;

  import augeas-extension {
    prefix augex;
  }

  augex:augeas-mod-name "Schroot";

  list schroot {
    key "config-file";
    leaf config-file {
      type string;
    }
    list record-list {
      key "_id";
      ordered-by user;
      leaf _id {
        type uint64;
        description
          "Implicitly generated list key to maintain the order of the augeas data.";
      }
      container record {
        augex:data-path "$$";
        presence "Config entry.";
        leaf record {
          mandatory true;
          type string {
            pattern "#commen((t[^\\]\n/]|[^\\]\n/t])[^\\]\n/]*|())|#comme([^\\]\n/n][^\\]\n/]*|())|#comm([^\\]\n/e][^\\]\n/]*|())|#com([^\\]\n/m][^\\]\n/]*|())|#co([^\\]\n/m][^\\]\n/]*|())|#c([^\\]\n/o][^\\]\n/]*|())|(#[^\\]\n/c]|[^\\]\n#/][^\\]\n/])[^\\]\n/]*|#|[^\\]\n#/]";
          }
        }
        list config-entries {
          key "_id";
          ordered-by user;
          leaf _id {
            type uint64;
            description
              "Implicitly generated list key to maintain the order of the augeas data.";
          }
          choice ch-config-entries {
            mandatory true;
            container node {
              augex:data-path "$$";
              augex:value-yang-path "value";
              presence "Config entry.";
              leaf label {
                mandatory true;
                type string {
                  pattern "descriptio((n[.0-9A-Z_a-z-]|[.0-9A-Z_a-mo-z-])[.0-9A-Z_a-z-]*|())|descripti([.0-9A-Z_a-np-z-][.0-9A-Z_a-z-]*|())|descript([.0-9A-Z_a-hj-z-][.0-9A-Z_a-z-]*|())|descrip([.0-9A-Z_a-su-z-][.0-9A-Z_a-z-]*|())|descri([.0-9A-Z_a-oq-z-][.0-9A-Z_a-z-]*|())|descr([.0-9A-Z_a-hj-z-][.0-9A-Z_a-z-]*|())|desc([.0-9A-Z_a-qs-z-][.0-9A-Z_a-z-]*|())|des([.0-9A-Z_abd-z-][.0-9A-Z_a-z-]*|())|de([.0-9A-Z_a-rt-z-][.0-9A-Z_a-z-]*|())|(d[.0-9A-Z_a-df-z-]|[A-Za-ce-z][.0-9A-Z_a-z-])[.0-9A-Z_a-z-]*|d|[A-Za-ce-z]";
                }
              }
              leaf value {
                type union {
                  type string {
                    pattern "([^\t\n \"#;])((((([^\n#;])+)*)([^\t\n \"#;])){0,1})";
                  }
                  type string {
                    pattern "(([^\"\n]*)(([;#])+))([^\"\n]*)";
                  }
                }
              }
            }
            container description {
              augex:data-path "description";
              augex:value-yang-path "value";
              presence "Config entry.";
              leaf lang {
                type string {
                  pattern "[A-Za-z][A-Za-z0-9._-]*";
                }
                augex:data-path "lang";
              }
              leaf value {
                type union {
                  type string {
                    pattern "([^\t\n \"#])((((([^\n#])+)*)([^\t\n \"#])){0,1})";
                  }
                  type string {
                    pattern "(([^\"\n]*)((#)+))([^\"\n]*)";
                  }
                }
              }
            }
          }
        }
      }
    }
  }
}
