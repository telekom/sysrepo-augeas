module rtadvd {
  yang-version 1.1;
  namespace "aug:rtadvd";
  prefix aug;

  import augeas-extension {
    prefix augex;
  }

  augex:augeas-mod-name "Rtadvd";

  list rtadvd {
    key "config-file";
    leaf config-file {
      type string;
    }
    list record-list {
      key "_id";
      ordered-by user;
      leaf _id {
        type uint64;
        description
          "Implicitly generated list key to maintain the order of the augeas data.";
      }
      container record {
        augex:data-path "record";
        presence "Config entry.";
        list name-list {
          key "_id";
          min-elements 1;
          ordered-by user;
          leaf _id {
            type uint64;
            description
              "Implicitly generated list key to maintain the order of the augeas data.";
          }
          leaf name {
            mandatory true;
            type string {
              pattern "[^#:\\\\\\\\\t\n|][^:\\\\\\\\\t\n|]*";
            }
            augex:data-path "name";
          }
        }
        list capability-list {
          key "_id";
          ordered-by user;
          leaf _id {
            type uint64;
            description
              "Implicitly generated list key to maintain the order of the augeas data.";
          }
          leaf capability {
            mandatory true;
            type string {
              pattern "[a-zA-Z0-9-]+(#?@|#[0-9]+|=(\"[^\"]*\"|[^:\"]*))?";
            }
            augex:data-path "capability";
          }
        }
      }
    }
  }
}
