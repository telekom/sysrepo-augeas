module nginx {
  yang-version 1.1;
  namespace "aug:nginx";
  prefix aug;

  import augeas-extension {
    prefix augex;
  }

  augex:augeas-mod-name "Nginx";

  grouping directive {
    choice ch-directive {
      mandatory true;
      container simple {
        augex:data-path "$$";
        augex:value-yang-path "value";
        presence "Config entry.";
        leaf label {
          mandatory true;
          type string {
            pattern "[A-Za-z0-9_.:-]+";
            pattern "http|events|server|mail|stream|if|location|geo|map|split_clients|upstream" {
              modifier invert-match;
            }
          }
        }
        leaf mask {
          type uint64;
          augex:data-path "mask";
        }
        leaf value {
          type string {
            pattern "[^ \t\n;#]([^\";#]|\"[^\"]*\\\")*";
          }
        }
      }
      container server {
        augex:data-path "@server";
        presence "Config entry.";
        leaf address {
          mandatory true;
          type string {
            pattern "[A-Za-z0-9_.:/-]+";
          }
          augex:data-path "@address";
        }
        list word-list {
          key "_id";
          ordered-by user;
          leaf _id {
            type uint64;
            description
              "Implicitly generated list key to maintain the order of the augeas data.";
          }
          container word {
            augex:data-path "$$";
            augex:value-yang-path "word";
            presence "Config entry.";
            leaf id {
              mandatory true;
              type string {
                pattern "[A-Za-z0-9_.:-]+";
              }
            }
            leaf word {
              type string {
                pattern "[A-Za-z0-9_.:-]+";
              }
            }
          }
        }
      }
    }
  }
  list nginx {
    key "config-file";
    leaf config-file {
      type string;
    }
    list config-entries {
      key "_id";
      ordered-by user;
      leaf _id {
        type uint64;
        description
          "Implicitly generated list key to maintain the order of the augeas data.";
      }
      choice ch-config-entries {
        mandatory true;
        case directive {
          uses directive;
        }
        list http-list {
          key "_r-id";
          leaf _r-id {
            type uint64;
            description
              "Implicitly generated list key to maintain the recursive augeas data.";
          }
          choice ch-http-list {
            mandatory true;
            container http {
              augex:data-path "http";
              presence "Config entry.";
              list config-entries {
                key "_id";
                ordered-by user;
                leaf _id {
                  type uint64;
                  description
                    "Implicitly generated list key to maintain the order of the augeas data.";
                }
                choice ch-config-entries {
                  mandatory true;
                  leaf _http-ref {
                    type leafref {
                      path "../../../../http-list/_r-id";
                    }
                    description
                      "Implicitly generated leaf to maintain recursive augeas data.";
                  }
                  case directive {
                    uses directive;
                  }
                }
              }
            }
            container events {
              augex:data-path "events";
              presence "Config entry.";
              list config-entries {
                key "_id";
                ordered-by user;
                leaf _id {
                  type uint64;
                  description
                    "Implicitly generated list key to maintain the order of the augeas data.";
                }
                choice ch-config-entries {
                  mandatory true;
                  leaf _http-ref {
                    type leafref {
                      path "../../../../http-list/_r-id";
                    }
                    description
                      "Implicitly generated leaf to maintain recursive augeas data.";
                  }
                  case directive {
                    uses directive;
                  }
                }
              }
            }
            container server {
              augex:data-path "server";
              presence "Config entry.";
              list config-entries {
                key "_id";
                ordered-by user;
                leaf _id {
                  type uint64;
                  description
                    "Implicitly generated list key to maintain the order of the augeas data.";
                }
                choice ch-config-entries {
                  mandatory true;
                  leaf _http-ref {
                    type leafref {
                      path "../../../../http-list/_r-id";
                    }
                    description
                      "Implicitly generated leaf to maintain recursive augeas data.";
                  }
                  case directive {
                    uses directive;
                  }
                }
              }
            }
            container mail {
              augex:data-path "mail";
              presence "Config entry.";
              list config-entries {
                key "_id";
                ordered-by user;
                leaf _id {
                  type uint64;
                  description
                    "Implicitly generated list key to maintain the order of the augeas data.";
                }
                choice ch-config-entries {
                  mandatory true;
                  leaf _http-ref {
                    type leafref {
                      path "../../../../http-list/_r-id";
                    }
                    description
                      "Implicitly generated leaf to maintain recursive augeas data.";
                  }
                  case directive {
                    uses directive;
                  }
                }
              }
            }
            container stream {
              augex:data-path "stream";
              presence "Config entry.";
              list config-entries {
                key "_id";
                ordered-by user;
                leaf _id {
                  type uint64;
                  description
                    "Implicitly generated list key to maintain the order of the augeas data.";
                }
                choice ch-config-entries {
                  mandatory true;
                  leaf _http-ref {
                    type leafref {
                      path "../../../../http-list/_r-id";
                    }
                    description
                      "Implicitly generated leaf to maintain recursive augeas data.";
                  }
                  case directive {
                    uses directive;
                  }
                }
              }
            }
            container if {
              augex:data-path "if";
              presence "Config entry.";
              leaf cond {
                mandatory true;
                type string {
                  pattern "\\(([^ \t\n{]|[ \t\n][^{])*\\)";
                }
                augex:data-path "#cond";
              }
              list config-entries {
                key "_id";
                ordered-by user;
                leaf _id {
                  type uint64;
                  description
                    "Implicitly generated list key to maintain the order of the augeas data.";
                }
                choice ch-config-entries {
                  mandatory true;
                  leaf _http-ref {
                    type leafref {
                      path "../../../../http-list/_r-id";
                    }
                    description
                      "Implicitly generated leaf to maintain recursive augeas data.";
                  }
                  case directive {
                    uses directive;
                  }
                }
              }
            }
            container location {
              augex:data-path "location";
              presence "Config entry.";
              leaf comp {
                type string {
                  pattern "=|~|~\\*|^~";
                }
                augex:data-path "#comp";
              }
              leaf uri {
                mandatory true;
                type string {
                  pattern "([^\" \t\n{][^ \t\n{]*)|(\"([^\\\\\"]|\\.)*\")";
                }
                augex:data-path "#uri";
              }
              list config-entries {
                key "_id";
                ordered-by user;
                leaf _id {
                  type uint64;
                  description
                    "Implicitly generated list key to maintain the order of the augeas data.";
                }
                choice ch-config-entries {
                  mandatory true;
                  leaf _http-ref {
                    type leafref {
                      path "../../../../http-list/_r-id";
                    }
                    description
                      "Implicitly generated leaf to maintain recursive augeas data.";
                  }
                  case directive {
                    uses directive;
                  }
                }
              }
            }
            container geo {
              augex:data-path "geo";
              presence "Config entry.";
              leaf address {
                type string {
                  pattern "([^\" \t\n{][^ \t\n{]*)|(\"([^\\\\\"]|\\.)*\")";
                }
                augex:data-path "#address";
              }
              leaf geo {
                mandatory true;
                type string {
                  pattern "([^\" \t\n{][^ \t\n{]*)|(\"([^\\\\\"]|\\.)*\")";
                }
                augex:data-path "#geo";
              }
              list config-entries {
                key "_id";
                ordered-by user;
                leaf _id {
                  type uint64;
                  description
                    "Implicitly generated list key to maintain the order of the augeas data.";
                }
                choice ch-config-entries {
                  mandatory true;
                  leaf _http-ref {
                    type leafref {
                      path "../../../../http-list/_r-id";
                    }
                    description
                      "Implicitly generated leaf to maintain recursive augeas data.";
                  }
                  case directive {
                    uses directive;
                  }
                }
              }
            }
            container map {
              augex:data-path "map";
              presence "Config entry.";
              leaf source {
                mandatory true;
                type string {
                  pattern "([^\" \t\n{][^ \t\n{]*)|(\"([^\\\\\"]|\\.)*\")";
                }
                augex:data-path "#source";
              }
              leaf variable {
                mandatory true;
                type string {
                  pattern "([^\" \t\n{][^ \t\n{]*)|(\"([^\\\\\"]|\\.)*\")";
                }
                augex:data-path "#variable";
              }
              list config-entries {
                key "_id";
                ordered-by user;
                leaf _id {
                  type uint64;
                  description
                    "Implicitly generated list key to maintain the order of the augeas data.";
                }
                choice ch-config-entries {
                  mandatory true;
                  leaf _http-ref {
                    type leafref {
                      path "../../../../http-list/_r-id";
                    }
                    description
                      "Implicitly generated leaf to maintain recursive augeas data.";
                  }
                  case directive {
                    uses directive;
                  }
                }
              }
            }
            container split-clients {
              augex:data-path "split_clients";
              presence "Config entry.";
              leaf string {
                mandatory true;
                type string {
                  pattern "([^\" \t\n{][^ \t\n{]*)|(\"([^\\\\\"]|\\.)*\")";
                }
                augex:data-path "#string";
              }
              leaf variable {
                mandatory true;
                type string {
                  pattern "([^\" \t\n{][^ \t\n{]*)|(\"([^\\\\\"]|\\.)*\")";
                }
                augex:data-path "#variable";
              }
              list config-entries {
                key "_id";
                ordered-by user;
                leaf _id {
                  type uint64;
                  description
                    "Implicitly generated list key to maintain the order of the augeas data.";
                }
                choice ch-config-entries {
                  mandatory true;
                  leaf _http-ref {
                    type leafref {
                      path "../../../../http-list/_r-id";
                    }
                    description
                      "Implicitly generated leaf to maintain recursive augeas data.";
                  }
                  case directive {
                    uses directive;
                  }
                }
              }
            }
            container upstream {
              augex:data-path "upstream";
              presence "Config entry.";
              leaf name {
                mandatory true;
                type string {
                  pattern "([^\" \t\n{][^ \t\n{]*)|(\"([^\\\\\"]|\\.)*\")";
                }
                augex:data-path "#name";
              }
              list config-entries {
                key "_id";
                ordered-by user;
                leaf _id {
                  type uint64;
                  description
                    "Implicitly generated list key to maintain the order of the augeas data.";
                }
                choice ch-config-entries {
                  mandatory true;
                  leaf _http-ref {
                    type leafref {
                      path "../../../../http-list/_r-id";
                    }
                    description
                      "Implicitly generated leaf to maintain recursive augeas data.";
                  }
                  case directive {
                    uses directive;
                  }
                }
              }
            }
          }
        }
      }
    }
  }
}
