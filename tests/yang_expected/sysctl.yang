module sysctl {
  yang-version 1.1;
  namespace "aug:sysctl";
  prefix aug;

  import augeas-extension {
    prefix augex;
  }

  augex:augeas-mod-name "Sysctl";

  list sysctl {
    key "config-file";
    leaf config-file {
      type string;
    }
    list entry-list {
      key "_id";
      ordered-by user;
      leaf _id {
        type uint64;
        description
          "Implicitly generated list key to maintain the order of the augeas data.";
      }
      container entry {
        augex:data-path "$$";
        augex:value-yang-path "value";
        presence "Config entry.";
        leaf label {
          mandatory true;
          type string {
            pattern "[*:/A-Za-z0-9_.-]+";
          }
        }
        leaf value {
          type union {
            type string {
              pattern "(('[^\n']*')|(\"[^\n\"]*\"))|([^\n \t'\"#][^\n#]*[^\n \t#]|[^\n \t'\"#])";
            }
            type string {
              pattern "";
            }
          }
        }
      }
    }
  }
}
