module group {
  yang-version 1.1;
  namespace "aug:group";
  prefix aug;

  import augeas-extension {
    prefix augex;
  }

  augex:augeas-mod-name "Group";

  grouping user-list {
    list user-list {
      key "_id";
      ordered-by user;
      leaf _id {
        type uint64;
        description
          "Implicitly generated list key to maintain the order of the augeas data.";
      }
      leaf user {
        mandatory true;
        type string {
          pattern "[A-Za-z0-9_.-]+";
        }
        augex:data-path "user";
      }
    }
  }
  list group {
    key "config-file";
    leaf config-file {
      type string;
    }
    list config-entries {
      key "_id";
      ordered-by user;
      leaf _id {
        type uint64;
        description
          "Implicitly generated list key to maintain the order of the augeas data.";
      }
      choice ch-config-entries {
        mandatory true;
        container entry {
          augex:data-path "$$";
          presence "Config entry.";
          leaf word {
            mandatory true;
            type string {
              pattern "[A-Za-z0-9_.-]+";
            }
          }
          leaf password {
            mandatory true;
            type string {
              pattern "[A-Za-z0-9_.!*-]*";
            }
            augex:data-path "password";
          }
          leaf gid {
            mandatory true;
            type uint64;
            augex:data-path "gid";
          }
          uses user-list;
        }
        container nisdefault {
          augex:data-path "@nisdefault";
          presence "Config entry.";
          leaf password {
            type union {
              type string {
                length 0;
              }
              type string {
                pattern "([A-Za-z0-9_.!*-]*){0,1}";
              }
            }
            augex:data-path "password";
          }
          leaf gid {
            type union {
              type string {
                length 0;
              }
              type uint64;
            }
            augex:data-path "gid";
          }
          uses user-list;
        }
      }
    }
  }
}
