module xendconfsxp {
  yang-version 1.1;
  namespace "aug:xendconfsxp";
  prefix aug;

  import augeas-extension {
    prefix augex;
  }

  augex:augeas-mod-name "Xendconfsxp";

  grouping item {
    leaf item {
      type string {
        pattern "[A-Za-z0-9_./-]+|\\\"([^\\\\\"\\\\\\\\]|(\\\\.))*\\\"|'([^'\\\\\\\\]|(\\\\.))*'";
      }
      augex:data-path "item";
    }
  }
  list xendconfsxp {
    key "config-file";
    leaf config-file {
      type string;
    }
    list sexpr-list {
      key "_id";
      ordered-by user;
      leaf _id {
        type uint64;
        description
          "Implicitly generated list key to maintain the order of the augeas data.";
      }
      container sexpr {
        augex:data-path "$$";
        presence "Config entry.";
        leaf var-name {
          mandatory true;
          type string {
            pattern "[A-Za-z0-9_.-]+";
          }
        }
        choice ch-sexpr {
          mandatory true;
          case item {
            uses item;
          }
          list array-list {
            key "_r-id";
            leaf _r-id {
              type uint64;
              description
                "Implicitly generated list key to maintain the recursive augeas data.";
            }
            container array {
              augex:data-path "array";
              presence "Config entry.";
              list config-entries {
                key "_id";
                min-elements 1;
                ordered-by user;
                leaf _id {
                  type uint64;
                  description
                    "Implicitly generated list key to maintain the order of the augeas data.";
                }
                choice ch-config-entries {
                  mandatory true;
                  leaf _array-ref {
                    type leafref {
                      path "../../../../array-list/_r-id";
                    }
                    description
                      "Implicitly generated leaf to maintain recursive augeas data.";
                  }
                  case item {
                    uses item;
                  }
                }
              }
            }
          }
        }
      }
    }
  }
}
