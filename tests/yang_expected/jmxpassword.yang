module jmxpassword {
  yang-version 1.1;
  namespace "aug:jmxpassword";
  prefix aug;

  import augeas-extension {
    prefix augex;
  }

  augex:augeas-mod-name "JMXPassword";

  list jmxpassword {
    key "config-file";
    leaf config-file {
      type string;
    }
    list pass-entry-list {
      key "_id";
      ordered-by user;
      leaf _id {
        type uint64;
        description
          "Implicitly generated list key to maintain the order of the augeas data.";
      }
      container user {
        augex:data-path "user";
        presence "Config entry.";
        leaf username {
          mandatory true;
          type string {
            pattern "[A-Za-z0-9_.-]+";
          }
          augex:data-path "username";
        }
        leaf password {
          mandatory true;
          type string {
            pattern "[^ \t\n]+";
          }
          augex:data-path "password";
        }
      }
    }
  }
}
