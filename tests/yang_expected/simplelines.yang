module simplelines {
  yang-version 1.1;
  namespace "aug:simplelines";
  prefix aug;

  import augeas-extension {
    prefix augex;
  }

  augex:augeas-mod-name "Simplelines";

  list simplelines {
    key "config-file";
    leaf config-file {
      type string;
    }
    list line-list {
      key "_seq";
      ordered-by user;
      augex:data-path "$$";
      augex:value-yang-path "value";
      leaf _seq {
        type uint64;
        description
          "Key contains some unique value. The order is based on the actual order of list instances.";
      }
      leaf value {
        type string {
          pattern "[^# \t\n].*[^ \t\n]|[^# \t\n]";
        }
      }
    }
  }
}
