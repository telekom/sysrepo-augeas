module securetty {
  yang-version 1.1;
  namespace "aug:securetty";
  prefix aug;

  import augeas-extension {
    prefix augex;
  }

  augex:augeas-mod-name "Securetty";

  list securetty {
    key "config-file";
    leaf config-file {
      type string;
    }
    list securetty-list {
      key "_seq";
      ordered-by user;
      augex:data-path "$$";
      augex:value-yang-path "word";
      leaf _seq {
        type uint64;
        description
          "Key contains some unique value. The order is based on the actual order of list instances.";
      }
      leaf word {
        type string {
          pattern "[^ \t\n#]+";
        }
      }
    }
  }
}
