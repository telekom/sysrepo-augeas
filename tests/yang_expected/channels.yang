module channels {
  yang-version 1.1;
  namespace "aug:channels";
  prefix aug;

  import augeas-extension {
    prefix augex;
  }

  augex:augeas-mod-name "Channels";

  grouping lang-list {
    list lang-list {
      key "_id";
      ordered-by user;
      leaf _id {
        type uint64;
        description
          "Implicitly generated list key to maintain the order of the augeas data.";
      }
      leaf lang {
        mandatory true;
        type string {
          pattern "[A-Za-z0-9_.-]+";
        }
        augex:data-path "lang";
      }
    }
  }
  grouping ch-lang-list {
    choice ch-lang-list {
      container case {
        presence "Config entry.";
        uses lang-list;
        leaf codec {
          type uint64;
          augex:data-path "codec";
        }
      }
      container case2 {
        presence "Config entry.";
        leaf codec {
          type uint64;
          augex:data-path "codec";
        }
      }
    }
  }
  grouping entry-list {
    list entry-list {
      key "_id";
      ordered-by user;
      leaf _id {
        type uint64;
        description
          "Implicitly generated list key to maintain the order of the augeas data.";
      }
      container entry {
        augex:data-path "entry";
        augex:value-yang-path "no-semicolon";
        presence "Config entry.";
        leaf no-semicolon {
          mandatory true;
          type string {
            pattern "[^;\n]+";
          }
        }
        leaf provider {
          type string {
            pattern "[^: \t\n][^:\n]*[^: \t\n]|[^:\n]";
          }
          augex:data-path "provider";
        }
        leaf frequency {
          mandatory true;
          type uint64;
          augex:data-path "frequency";
        }
        leaf parameter {
          mandatory true;
          type string {
            pattern "[A-Za-z0-9_.-]+";
          }
          augex:data-path "parameter";
        }
        leaf signal-source {
          mandatory true;
          type string {
            pattern "[A-Za-z0-9_.-]+";
          }
          augex:data-path "signal_source";
        }
        leaf symbol-rate {
          mandatory true;
          type uint64;
          augex:data-path "symbol_rate";
        }
        container vpid {
          augex:data-path "vpid";
          augex:value-yang-path "integer";
          presence "Config entry.";
          leaf integer {
            mandatory true;
            type uint64;
          }
          leaf codec {
            type uint64;
            augex:data-path "codec";
          }
        }
        container vpid-pcr {
          augex:data-path "vpid_pcr";
          augex:value-yang-path "integer";
          presence "Config entry.";
          leaf integer {
            mandatory true;
            type uint64;
          }
          leaf codec {
            type uint64;
            augex:data-path "codec";
          }
        }
        list apid-list {
          key "_id";
          min-elements 1;
          ordered-by user;
          leaf _id {
            type uint64;
            description
              "Implicitly generated list key to maintain the order of the augeas data.";
          }
          container apid {
            augex:data-path "apid";
            augex:value-yang-path "integer";
            presence "Config entry.";
            leaf integer {
              mandatory true;
              type uint64;
            }
            uses ch-lang-list;
          }
        }
        list apid-dolby-list {
          key "_id";
          ordered-by user;
          leaf _id {
            type uint64;
            description
              "Implicitly generated list key to maintain the order of the augeas data.";
          }
          container apid-dolby {
            augex:data-path "apid_dolby";
            augex:value-yang-path "integer";
            presence "Config entry.";
            leaf integer {
              mandatory true;
              type uint64;
            }
            uses ch-lang-list;
          }
        }
        leaf tpid {
          mandatory true;
          type uint64;
          augex:data-path "tpid";
        }
        list tpid-bylang-list {
          key "_id";
          ordered-by user;
          leaf _id {
            type uint64;
            description
              "Implicitly generated list key to maintain the order of the augeas data.";
          }
          container tpid-bylang {
            augex:data-path "tpid_bylang";
            augex:value-yang-path "integer";
            presence "Config entry.";
            leaf integer {
              mandatory true;
              type uint64;
            }
            uses lang-list;
          }
        }
        list caid-list {
          key "_id";
          min-elements 1;
          ordered-by user;
          leaf _id {
            type uint64;
            description
              "Implicitly generated list key to maintain the order of the augeas data.";
          }
          leaf caid {
            mandatory true;
            type string {
              pattern "[A-Za-z0-9_.-]+";
            }
            augex:data-path "caid";
          }
        }
        leaf sid {
          mandatory true;
          type uint64;
          augex:data-path "sid";
        }
        leaf nid {
          mandatory true;
          type uint64;
          augex:data-path "nid";
        }
        leaf tid {
          mandatory true;
          type uint64;
          augex:data-path "tid";
        }
        leaf rid {
          mandatory true;
          type uint64;
          augex:data-path "rid";
        }
      }
    }
  }
  list channels {
    key "config-file";
    leaf config-file {
      type string;
    }
    uses entry-list;
    list group-list {
      key "_id";
      ordered-by user;
      leaf _id {
        type uint64;
        description
          "Implicitly generated list key to maintain the order of the augeas data.";
      }
      container group {
        augex:data-path "group";
        augex:value-yang-path "no-colon";
        presence "Config entry.";
        leaf no-colon {
          mandatory true;
          type string {
            pattern "[^: \t\n][^:\n]*[^: \t\n]|[^:\n]";
          }
        }
        uses entry-list;
      }
    }
  }
}
