module pam {
  yang-version 1.1;
  namespace "aug:pam";
  prefix aug;

  import augeas-extension {
    prefix augex;
  }

  augex:augeas-mod-name "Pam";

  list pam {
    key "config-file";
    leaf config-file {
      type string;
    }
    list config-entries {
      key "_id";
      ordered-by user;
      leaf _id {
        type uint64;
        description
          "Implicitly generated list key to maintain the order of the augeas data.";
      }
      choice ch-config-entries {
        mandatory true;
        leaf include {
          type string {
            pattern "([^# \t\n\\\\]|\\\\.)+";
          }
          augex:data-path "include";
        }
        container record-svc {
          augex:data-path "$$";
          presence "Config entry.";
          leaf record {
            mandatory true;
            type uint64;
          }
          leaf optional {
            type empty;
            augex:data-path "optional";
          }
          leaf type {
            mandatory true;
            type string {
              pattern "(?i)auth|session|account|password";
            }
            augex:data-path "type";
          }
          leaf control {
            mandatory true;
            type string {
              pattern "\\[[^\\]#\n]*\\]|[a-zA-Z]+";
            }
            augex:data-path "control";
          }
          leaf module {
            mandatory true;
            type string {
              pattern "([^# \t\n\\\\]|\\\\.)+";
            }
            augex:data-path "module";
          }
          list argument-list {
            key "_id";
            ordered-by user;
            leaf _id {
              type uint64;
              description
                "Implicitly generated list key to maintain the order of the augeas data.";
            }
            leaf argument {
              mandatory true;
              type string {
                pattern "\\[[^\\]#\n]+\\]|[^\\[#\n \t\\\\][^#\n \t\\\\]*";
              }
              augex:data-path "argument";
            }
          }
        }
      }
    }
  }
}
