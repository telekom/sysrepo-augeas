module updatedb {
  yang-version 1.1;
  namespace "aug:updatedb";
  prefix aug;

  import augeas-extension {
    prefix augex;
  }

  augex:augeas-mod-name "UpdateDB";

  grouping entry-list {
    list entry-list {
      key "_id";
      min-elements 1;
      ordered-by user;
      leaf _id {
        type uint64;
        description
          "Implicitly generated list key to maintain the order of the augeas data.";
      }
      leaf entry {
        mandatory true;
        type string {
          pattern "[^ \t\n]+";
        }
        augex:data-path "entry";
      }
    }
  }
  list updatedb {
    key "config-file";
    leaf config-file {
      type string;
    }
    list config-entries {
      key "_id";
      ordered-by user;
      leaf _id {
        type uint64;
        description
          "Implicitly generated list key to maintain the order of the augeas data.";
      }
      choice ch-config-entries {
        mandatory true;
        container prunefs {
          augex:data-path "PRUNEFS";
          presence "Config entry.";
          uses entry-list;
        }
        container prunenames {
          augex:data-path "PRUNENAMES";
          presence "Config entry.";
          uses entry-list;
        }
        container prunepaths {
          augex:data-path "PRUNEPATHS";
          presence "Config entry.";
          uses entry-list;
        }
        leaf prune-bind-mounts {
          type string {
            pattern "[01]|no|yes";
          }
          augex:data-path "PRUNE_BIND_MOUNTS";
        }
      }
    }
  }
}
