module fstab {
  yang-version 1.1;
  namespace "aug:fstab";
  prefix aug;

  import augeas-extension {
    prefix augex;
  }

  augex:augeas-mod-name "Fstab";

  list fstab {
    key "config-file";
    leaf config-file {
      type string;
    }
    list mntent-list {
      key "_seq";
      ordered-by user;
      augex:data-path "$$";
      leaf _seq {
        type uint64;
        description
          "Key contains some unique value. The order is based on the actual order of list instances.";
      }
      leaf spec {
        mandatory true;
        type string {
          pattern "[^,# \n\t][^ \n\t]*";
        }
        augex:data-path "spec";
      }
      leaf file {
        mandatory true;
        type string {
          pattern "[^# \t\n]+";
        }
        augex:data-path "file";
      }
      list vfstype-list {
        key "_id";
        min-elements 1;
        ordered-by user;
        leaf _id {
          type uint64;
          description
            "Implicitly generated list key to maintain the order of the augeas data.";
        }
        container vfstype {
          augex:data-path "vfstype";
          augex:value-yang-path "optlabel";
          presence "Config entry.";
          leaf optlabel {
            mandatory true;
            type string {
              pattern "[^,#= \n\t]+";
            }
          }
          leaf value {
            type union {
              type empty;
              type string {
                pattern "[^,# \n\t]+";
              }
            }
            augex:data-path "value";
          }
        }
      }
      list opt-list {
        key "_id";
        ordered-by user;
        leaf _id {
          type uint64;
          description
            "Implicitly generated list key to maintain the order of the augeas data.";
        }
        container opt {
          augex:data-path "opt";
          augex:value-yang-path "optlabel";
          presence "Config entry.";
          leaf optlabel {
            mandatory true;
            type string {
              pattern "[^,#= \n\t]+";
            }
          }
          leaf value {
            type union {
              type empty;
              type string {
                pattern "[^,# \n\t]+";
              }
            }
            augex:data-path "value";
          }
        }
      }
      leaf dump {
        type uint64;
        augex:data-path "dump";
      }
      leaf passno {
        type uint64;
        augex:data-path "passno";
      }
    }
  }
}
