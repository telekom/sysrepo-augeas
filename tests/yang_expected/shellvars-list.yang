module shellvars-list {
  yang-version 1.1;
  namespace "aug:shellvars-list";
  prefix aug;

  import augeas-extension {
    prefix augex;
  }

  augex:augeas-mod-name "Shellvars_list";

  list shellvars-list {
    key "config-file";
    leaf config-file {
      type string;
    }
    list kv-list {
      key "_id";
      ordered-by user;
      leaf _id {
        type uint64;
        description
          "Implicitly generated list key to maintain the order of the augeas data.";
      }
      container kv {
        augex:data-path "$$";
        presence "Config entry.";
        leaf key {
          mandatory true;
          type string {
            pattern "[A-Za-z0-9_]+";
          }
        }
        leaf quote {
          mandatory true;
          type union {
            type string {
              pattern "'";
            }
            type string {
              pattern "\"";
            }
            type string {
              pattern "";
            }
          }
          augex:data-path "quote";
        }
        choice ch-kv {
          list value-list {
            key "_id";
            //when "re-match(../quote, ''')";
            ordered-by user;
            leaf _id {
              type uint64;
              description
                "Implicitly generated list key to maintain the order of the augeas data.";
            }
            leaf value {
              mandatory true;
              type string {
                pattern "[^ '\t\n]+";
              }
              augex:data-path "value";
            }
          }
          list value-list2 {
            key "_id";
            when "re-match(../quote, '\"')";
            ordered-by user;
            leaf _id {
              type uint64;
              description
                "Implicitly generated list key to maintain the order of the augeas data.";
            }
            leaf value {
              mandatory true;
              type string {
                pattern "([^ \"\\\\\t\n]|\\\\.)+";
              }
              augex:data-path "value";
            }
          }
          leaf value {
            type string {
              pattern "((([^ `\"'\\\\\t\n]|\\\\.)+)+)|(`[^`\n]*`)";
            }
            augex:data-path "value";
            when "../quote=''";
          }
        }
      }
    }
  }
}
