module postfix_sasl_smtpd {
  namespace "aug:postfix_sasl_smtpd";
  prefix aug;

  import augeas-extension {
    prefix augex;
  }

  container postfix_sasl_smtpd {
    list list {
      key "key";
      leaf key {
        type string {
          pattern "pwcheck_method";
        }
        augex:data-path "$key";
      }
      leaf value_to_eol {
        type string {
          pattern "[^ \t\n].*[^ \t\n]|[^ \t\n]";
        }
        augex:data-path "$key";
      }
    }
    list list2 {
      key "key";
      leaf key {
        type string {
          pattern "auxprop_plugin";
        }
        augex:data-path "$key";
      }
      leaf value_to_eol {
        type string {
          pattern "[^ \t\n].*[^ \t\n]|[^ \t\n]";
        }
        augex:data-path "$key";
      }
    }
    list list3 {
      key "key";
      leaf key {
        type string {
          pattern "saslauthd_path";
        }
        augex:data-path "$key";
      }
      leaf value_to_eol {
        type string {
          pattern "[^ \t\n].*[^ \t\n]|[^ \t\n]";
        }
        augex:data-path "$key";
      }
    }
    list list4 {
      key "key";
      leaf key {
        type string {
          pattern "mech_list";
        }
        augex:data-path "$key";
      }
      leaf value_to_eol {
        type string {
          pattern "[^ \t\n].*[^ \t\n]|[^ \t\n]";
        }
        augex:data-path "$key";
      }
    }
    list list5 {
      key "key";
      leaf key {
        type string {
          pattern "sql_engine";
        }
        augex:data-path "$key";
      }
      leaf value_to_eol {
        type string {
          pattern "[^ \t\n].*[^ \t\n]|[^ \t\n]";
        }
        augex:data-path "$key";
      }
    }
    list list6 {
      key "key";
      leaf key {
        type string {
          pattern "log_level";
        }
        augex:data-path "$key";
      }
      leaf value_to_eol {
        type string {
          pattern "[^ \t\n].*[^ \t\n]|[^ \t\n]";
        }
        augex:data-path "$key";
      }
    }
    list list7 {
      key "key";
      leaf key {
        type string {
          pattern "auto_transition";
        }
        augex:data-path "$key";
      }
      leaf value_to_eol {
        type string {
          pattern "[^ \t\n].*[^ \t\n]|[^ \t\n]";
        }
        augex:data-path "$key";
      }
    }
  }
}
