module iscsid {
  namespace "aug:iscsid";
  prefix aug;

  import augeas-extension {
    prefix augex;
  }

  container iscsid {
    list kv {
      key "key_re";
      leaf key_re {
        type string {
          pattern "[][A-Za-z0-9_.-]+";
        }
        augex:data-path "$key_re";
      }
      leaf value_re {
        type string {
          pattern "[^ \t\n](.*[^ \t\n])?";
        }
        augex:data-path "$key_re";
      }
    }
  }
}
