module simplelines {
  namespace "aug:simplelines";
  prefix aug;

  import augeas-extension {
    prefix augex;
  }

  container simplelines {
    leaf-list line {
      type string {
        pattern "[^# \t\n].*[^ \t\n]|[^# \t\n]";
      }
      augex:data-path "$AY_UINT";
    }
  }
}
